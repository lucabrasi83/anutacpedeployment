module cpedeployment {
  yang-version 1.1;
  namespace "http://anutanetworks.com/cpedeployment";
  prefix cpedeployment;

  import controller {
    prefix ac;
  }
  import device {
    prefix dev;
  }
  import interface {
    prefix if;
  }
  import interface-ext {
    prefix if-ext;
  }
  import ipam {
    prefix ip;
  }
  import resourcepool {
    prefix rp;
  }
  import service-manager {
    prefix sm;
  }
  import vrouter-feature {
    prefix vrf;
  }
  import interconnect-feature {
    prefix ic;
  }
  import virtual-network-feature {
    prefix vnf;
  }
  import external-network-feature {
    prefix enf;
  }
  import ncx-extensions {
    prefix n-ext;
  }
  import ncx-ui-extensions {
    prefix n-ext-ui;
  }
  import ietf-inet-types {
    prefix inet;
  }
  import hsrp {
    prefix hsrp;
  }
  import l3features {
    prefix l3;
  }
  import qos {
    prefix qos;
  }
  import dmvpn {
    prefix dmvpn;
  }
  import cpe {
    prefix cpe;
  }
  import acl {
    prefix acl;
  }
  import wanoptimizer-feature {
    prefix wanop;
  }
  import wanoptimizer {
    prefix wanop-device;
  }
  import basicDeviceConfigs {
    prefix basicDeviceConfigs;
  }
  import l2features {
    prefix l2;
  }

  organization
    "Anuta Networks";
  description
    "This module contains a collection of YANG definitions for
      TATA Communications CPE Service ";

  revision 2016-06-30 {
    description
      "Initial revision";
  }

  typedef interface-type {
    type enumeration {
      enum "Physical";
      enum "SVI";
      enum "Sub-Interface";
    }
  }

  typedef interface-type1 {
    type enumeration {
      enum "Physical";
      enum "SVI";
      enum "Sub-Interface";
      enum "Tunnel";
    }
  }

  typedef condition-type {
    type enumeration {
      enum "permit";
      enum "deny";
    }
  }

  typedef community-list-entry-type {
    type enumeration {
      enum "standard";
      enum "expanded";
    }
  }

  typedef access-list-entry-type {
    type enumeration {
      enum "extended";
      enum "standard";
    }
  }

  typedef peer-group {
    type leafref {
      //path "../../../../../../bgp-peer-groups/bgp-peer-group/peer-group";
      path "/ac:services/cpedeployment:managed-cpe-services/customer[name=current()/../../../../../../name]/bgp-peer-groups/bgp-peer-group/peer-group";
    }
  }

  typedef route-map-condition-types {
    type enumeration {
      enum "interface";
      enum "tag";
      enum "acl";
      enum "prefix-list";
      enum "route-source";
      enum "source-protocol";
      enum "community";
      enum "metric";
      enum "as-path";
      enum "next-hop";
      enum "address";
      enum "extcommunity";
    }
  }

  typedef access-id {
    type enumeration {
      enum "ro";
      enum "rw";
    }
  }

  typedef route-update {
    type enumeration {
      enum "in";
      enum "out";
    }
  }

  typedef default-inf-key {
    type enumeration {
      enum "metric";
      enum "metric-type";
      enum "route-map";
    }
  }

  typedef key {
    type enumeration {
      enum "metric";
      enum "metric-type";
    }
  }

  typedef ospf-protocol {
    type enumeration {
      enum "bgp";
      enum "ospf";
      enum "eigrp";
      enum "connected";
      enum "static";
    }
  }

  typedef route-map-set-types {
    type enumeration {
      enum "local-preference";
      enum "metric";
      enum "metric-type";
      enum "as-path";
      enum "tag";
      enum "community";
      enum "next-hop";
      enum "as-path prepend";
      enum "vrf";
      enum "ip";
      enum "origin";
      enum "weight";
      enum "comm-list";
    }
  }

  typedef ip-types {
    type enumeration {
      enum "precedence";
      enum "next-hop";
      enum "df";
      enum "qos-group";
    }
  }

  typedef precedence-type {
    type enumeration {
      enum "routine";
      enum "priority";
      enum "immediate";
      enum "flash";
      enum "flash-override";
      enum "critical";
      enum "internet";
      enum "network";
    }
  }

  typedef match-packets-type {
    type enumeration {
      enum "precedence";
      enum "dscp";
      enum "echo";
      enum "log";
      enum "echo-reply";
      enum "established";
      enum "fragments";
      enum "ttl-exceeded";
      enum "ttl";
      enum "tos";
      enum "port-unreachable";
      enum "log-input";
    }
  }

  typedef set-values {
    type union {
      type string-no-lead-trail-space;
      type precedence-type;
    }
  }

  typedef action-type {
    type enumeration {
      enum "permit";
      enum "deny";
    }
  }

  typedef match-type-def {
    type enumeration {
      enum "match-all";
      enum "match-any";
    }
  }

  typedef matching-prefix-type {
    type string {
      pattern "^(([0-9])|([1-2][0-9])|(3[0-2]))$";
    }
  }

  typedef string-no-space {
    type string {
      pattern "^(\\S*)$";
    }
  }

  typedef string-no-lead-trail-space {
    type string {
      //pattern "^(\\S?)(?!\\s)(.*)(\\S+)$";
      pattern "^(\\S?)(.*)(\\S+)$";
    }
  }

  //typedef mac-address {
  //type string {
  //pattern "[0-9a-fA-F]{4}(.[0-9a-fA-F]{4}){3}";
  //}
  //}

  typedef qos-group-def {
    type enumeration {
      enum "0";
      enum "1";
      enum "3";
      enum "4";
      enum "5";
      enum "6";
      enum "7";
      enum "8";
      enum "9";
      enum "10";
      enum "11";
      enum "12";
      enum "13";
      enum "14";
      enum "15";
      enum "16";
      enum "17";
      enum "18";
      enum "19";
      enum "20";
      enum "21";
      enum "22";
      enum "23";
      enum "24";
      enum "25";
      enum "26";
      enum "27";
      enum "28";
      enum "29";
      enum "30";
      enum "31";
      enum "32";
      enum "33";
      enum "34";
      enum "35";
      enum "36";
      enum "37";
      enum "38";
      enum "39";
      enum "40";
      enum "41";
      enum "42";
      enum "43";
      enum "44";
      enum "45";
      enum "46";
      enum "47";
      enum "48";
      enum "49";
      enum "50";
      enum "51";
      enum "52";
      enum "53";
      enum "54";
      enum "55";
      enum "56";
      enum "57";
      enum "58";
      enum "59";
      enum "60";
      enum "61";
      enum "62";
      enum "63";
      enum "64";
      enum "65";
      enum "66";
      enum "67";
      enum "68";
      enum "69";
      enum "70";
      enum "71";
      enum "72";
      enum "73";
      enum "74";
      enum "75";
      enum "76";
      enum "77";
      enum "78";
      enum "79";
      enum "80";
      enum "81";
      enum "82";
      enum "83";
      enum "84";
      enum "85";
      enum "86";
      enum "87";
      enum "88";
      enum "89";
      enum "90";
      enum "91";
      enum "92";
      enum "93";
      enum "94";
      enum "95";
      enum "96";
      enum "97";
      enum "98";
      enum "99";
    }
  }

  typedef crypto-version {
    type enumeration {
      enum "IKEV1";
      enum "IKEV2";
    }
  }

  typedef encryption {
    type enumeration {
      enum "DES";
      enum "3DES";
      enum "AES128";
      enum "AES192";
      enum "AES256";
    }
  }

  typedef encryption_transform {
    type enumeration {
      enum "esp-aes";
      enum "esp-3des";
      enum "esp-des";
      enum "esp-aes 128";
      enum "esp-aes 192";
      enum "esp-aes 256";
      enum "esp-gcm 256";
    }
  }

  typedef authentication {
    type enumeration {
      enum "MD5";
      enum "SHA1";
      enum "SHA256";
      enum "SHA384";
      enum "SHA512";
    }
  }

  typedef authentication_transform {
    type enumeration {
      enum "esp-md5-hmac";
      enum "esp-sha-hmac";
      enum "esp-sha256-hmac";
      enum "esp-sha384-hmac";
      enum "esp-sha512-hmac";
    }
  }

  typedef ipsec-mode {
    type enumeration {
      enum "transport";
      enum "tunnel";
    }
  }

  typedef operation-def {
    type enumeration {
      enum "CREATE";
      enum "DELETE";
    }
  }

  typedef eigrp-protocol {
    type enumeration {
      enum "connected";
      enum "eigrp";
      enum "ospf";
      enum "bgp";
      enum "static";
    }
  }

  typedef table-def {
    type enumeration {
      enum "multicast";
      enum "unicast";
    }
  }

  typedef auth-mode {
    type enumeration {
      enum "pre-share";
      enum "rsa-sig";
    }
  }

  typedef dscp-values-type {
    description
      "dscp-code-all-values-type";
    type enumeration {
      enum "af11" {
        description
          "DSCP 10";
      }
      enum "af12" {
        description
          "DSCP 12";
      }
      enum "af13" {
        description
          "DSCP 14";
      }
      enum "af21" {
        description
          "DSCP 18";
      }
      enum "af22" {
        description
          "DSCP 20";
      }
      enum "af23" {
        description
          "DSCP 22";
      }
      enum "af31" {
        description
          "DSCP 26";
      }
      enum "af32" {
        description
          "DSCP 28";
      }
      enum "af33" {
        description
          "DSCP 30";
      }
      enum "af41" {
        description
          "DSCP 34";
      }
      enum "af42" {
        description
          "DSCP 36";
      }
      enum "af43" {
        description
          "DSCP 38";
      }
      enum "cs0" {
        description
          "Class selector 000 000 (0)";
      }
      enum "cs1" {
        description
          "Class Selector 001 000 (8)";
      }
      enum "cs2" {
        description
          "Class Selector 010 000 (16)";
      }
      enum "cs3" {
        description
          "Class Selector 011 000 (24)";
      }
      enum "cs4" {
        description
          "Class Selector 100 000 (32)";
      }
      enum "cs5" {
        description
          "Class Selector 101 000 (40)";
      }
      enum "cs6" {
        description
          "Class Selector 110 000 (48)";
      }
      enum "cs7" {
        description
          "Class Selector 111 000 (56)";
      }
      enum "default" {
        description
          "Default forwarding 000 000 (0)";
      }
      enum "ef" {
        description
          "Expedited forwarding 101 110 (46)";
      }
      enum "all" {
        description
          "All classes";
      }
      enum "0";
      enum "1";
      enum "3";
      enum "4";
      enum "5";
      enum "6";
      enum "7";
      enum "8";
      enum "9";
      enum "10";
      enum "11";
      enum "12";
      enum "13";
      enum "14";
      enum "15";
      enum "16";
      enum "17";
      enum "18";
      enum "19";
      enum "20";
      enum "21";
      enum "22";
      enum "23";
      enum "24";
      enum "25";
      enum "26";
      enum "27";
      enum "28";
      enum "29";
      enum "30";
      enum "31";
      enum "32";
      enum "33";
      enum "34";
      enum "35";
      enum "36";
      enum "37";
      enum "38";
      enum "39";
      enum "40";
      enum "41";
      enum "42";
      enum "43";
      enum "44";
      enum "45";
      enum "46";
      enum "47";
      enum "48";
      enum "49";
      enum "50";
      enum "51";
      enum "52";
      enum "53";
      enum "54";
      enum "55";
      enum "56";
      enum "57";
      enum "58";
      enum "59";
      enum "60";
      enum "61";
      enum "62";
      enum "63";
    }
  }

  typedef random-detect-def {
    type enumeration {
      enum "dscp-based";
      enum "discard-class-based";
      enum "precedence-based";
      enum "default";
      enum "none";
    }
  }

  typedef priority-level-def {
    type uint32 {
      range "1..2";
    }
  }

  typedef percentage-def {
    type uint8 {
      range "1..100";
    }
    units "percent";
    description
      "percentage";
  }

  typedef protocol-def {
    type enumeration {
      enum "ftp";
      enum "ftp-data";
      enum "ftp-agent";
      enum "http";
      enum "secure-http";
      enum "microsoftds";
      enum "smtp";
      enum "ntp";
      enum "bgp";
      enum "ospf";
      enum "eigrp";
      enum "netflow";
      enum "snmp";
      enum "ssh";
      enum "syslog";
      enum "tacacs";
      enum "exchange";
      enum "http url";
      enum "lotus-notes";
      enum "dropbox";
      enum "cifs";
      enum "tftp";
      enum "sftp";
      enum "sip";
      enum "h323";
      enum "ms-lync";
      enum "ms-lync-control";
      enum "ms-lync-media";
      enum "ms-lync-audio";
      enum "ms-lync-video";
      enum "ms-office-web-apps";
      enum "rtp";
      enum "rtp video";
      enum "rtp audio";
      enum "rtp-audio";
      enum "rtp-video";
      enum "ms-update";
      enum "ms-office-365";
      enum "sap";
      enum "active-directory";
      enum "salesforce";
      enum "share-point";
      enum "citrix";
      enum "citrix-audio";
      enum "citrix-static";
      enum "teamviewer";
      enum "lwapp";
      enum "amazon-web-services";
      enum "apple-app-store";
      enum "apple-ios-updates";
      enum "telnet";
      enum "gmail";
      enum "ms-wbt";
      enum "youtube";
      enum "windows-azure";
      enum "windows-store";
      enum "web-rtc";
      enum "whatsapp";
      enum "twitter";
      enum "sqlserver";
      enum "outlook-web-service";
      enum "ora-srv";
      enum "oracle-bi";
      enum "oracle-ebsuite-unsecured";
      enum "oracle-sqlnet";
      enum "netflix";
      enum "msexch-routing";
      enum "mcafee-update";
      enum "mcafee-antivirus";
      enum "jabber";
      enum "google-docs";
      enum "google-earth";
      enum "google-play";
      enum "google-plus";
      enum "google-services";
      enum "google-services-audio";
      enum "google-services-video";
      enum "google-services-media";
      enum "facebook";
      enum "facebook-audio";
      enum "facebook-media";
      enum "facebook-video";
      enum "facetime";
      enum "cisco-collab-audio";
      enum "cisco-collab-control";
      enum "cisco-collab-video";
      enum "cisco-collaboration";
      enum "cisco-jabber-audio";
      enum "cisco-jabber-control";
      enum "cisco-jabber-video";
      enum "cisco-media-audio";
      enum "cisco-media-video";
      enum "cisco-spark";
      enum "cisco-spark-audio";
      enum "cisco-spark-media";
      enum "cisco-spark-video";
      enum "skinny";
      enum "synergy";
      enum "vmware-fdm";
      enum "vmware-view";
      enum "vmware-vmotion";
      enum "vmware-vsphere";
      enum "rtcp";
      enum "ms-sql-m";
      enum "sip-tls";
      enum "stun-nat";
      enum "rdp";
      enum "icmp";
      enum "mgcp";
    }
  }

  typedef traffic-class-def {
    type enumeration {
      enum "broadcast-video" {
        description
          "Broadcast TV, live events, video surveillance";
      }
      enum "bulk-data" {
        description
          "Non-interactive data applications";
      }
      enum "multimedia-conferencing" {
        description
          "Desktop software multimedia collaboration applications";
      }
      enum "multimedia-streaming" {
        description
          "Video-on-Demand (VoD) streaming video";
      }
      enum "network-control" {
        description
          "Network control plane traffic";
      }
      enum "ops-admin-mgmt" {
        description
          "Network operations, administration, and management traffic";
      }
      enum "real-time-interactive" {
        description
          "High-definition interactive video applications";
      }
      enum "signaling" {
        description
          "Signaling traffic that supports IP voice and video telephony";
      }
      enum "transactional-data" {
        description
          "Interactive data applications";
      }
      enum "voip-telephony" {
        description
          "VoIP telephony (bearer-only) traffic";
      }
    }
  }

  grouping policy-bit-rate-def {
    description
      "policy-bit-rate-def";
    leaf bit-rate {
      type uint64 {
        range "8000..10000000000";
      }
      description
        "bit-rate 8000-10000000000";
    }
    leaf bit-rate-percent {
      type uint8 {
        range "0..100";
      }
      description
        "bit-rate-percent";
    }
  }

  grouping marking-priority-def {
    description
      "marking-priority-def";
    choice marking-priority {
      description
        "mark-priority";
      case drop-precedence {
        leaf drop-precedence {
          type union {
            type uint8 {
              range "1..7";
            }
            type enumeration {
              enum "ignore" {
                description
                  "ignore";
              }
            }
          }
          description
            "drop-precedence";
        }
      }
      case af-drop {
        leaf af-drop {
          type uint8 {
            range "1..3";
          }
          description
            "af-drop";
        }
      }
    }
  }

  grouping rate-option-def {
    description
      "rate-option-def";
    choice burst-option {
      description
        "burst-option";
      case burst {
        leaf burst {
          type uint32 {
            range "1..4250000000";
          }
          units "byte";
          description
            "burst";
        }
      }
      case time-burst {
        leaf time-burst {
          type uint32 {
            range "1..10000";
          }
          units "millisecond";
          description
            "time-burst";
        }
      }
    }
    choice excess-burst-option {
      description
        "excess-burst-option";
      case excess-burst {
        leaf excess-burst {
          type uint32 {
            range "1..4250000000";
          }
          units "byte";
          description
            "excess-burst";
        }
      }
      case time-excess-burst {
        leaf time-excess-burst {
          type uint32 {
            range "1..10000";
          }
          description
            "time-excess-burst";
        }
      }
    }
  }

  grouping rate-percentage-def {
    description
      "rate-percentage-def";
    leaf percentage {
      type uint8 {
        range "1..100";
      }
      units "percent";
      description
        "percentage";
    }
  }

  grouping bridge-def {
    leaf enable-vcaas-bridge {
      type boolean;
      description
        "Check to configure VCaaS L3 Bridge";
    }
    leaf interface-bridge-group {
      type uint8;
      description
        "Enter Bridge Group ID";
      when " ../enable-vcaas-bridge = 'true' ";
    }
    leaf interface-mac-acl {
      type uint16 {
        range "700..799";
      }
      description
        "Enter MAC Address ACL Number";
      when " ../create-bvi-interface = 'true' ";
    }
    leaf create-bvi-interface {
      type boolean;
      description
        "Check to create a Bridge Virtual Interface";
    }
    leaf bvi-interface-number {
      type uint8;
      description
        "Enter BVI Interface ID";
      when " ../create-bvi-interface = 'true' ";
    }
    leaf bvi-interface-ip {
      type inet:ipv4-address;
      description
        "Enter BVI Interface IP";
      when " ../create-bvi-interface = 'true' ";
    }
    leaf bvi-interface-mask {
      type inet:ipv4-address;
      description
        "Enter BVI Interface Mask";
      when " ../create-bvi-interface = 'true' ";
    }
  }

  grouping mac-acl-def {
    leaf acl-number {
      type uint16 {
        range "700..799";
      }
      description
        "Enter MAC Address ACL Number";
    }
    list access-list-rules {
      key "name action source-mac";
      leaf name {
        type string-no-lead-trail-space;
        description
          "Enter ACL Rule Name
           This is an internal field for Anuta NCX";
      }
      leaf action {
        type enumeration {
          enum "permit";
          enum "deny";
        }
        description
          "Select ACL rule action";
      }
      leaf source-mac {
        type string;
        description
          "Enter Source MAC Address";
      }
      leaf source-mac-mask {
        type string;
        description
          "Enter MAC Address Mask";
      }
      leaf destination-mac {
        type string;
        description
          "Enter MAC Address Mask";
        config false;
      }
    }
  }

  grouping rate-conform-def {
    description
      "rate-conform-def";
    container conform-handling {
      description
        "conform-handling";
      choice options {
        description
          "options";
        case mark-packet {
          uses marking-def;
        }
        case no-action {
          leaf no-action {
            type empty;
            description
              "no-action";
          }
        }
      }
    }
  }

  grouping marking-def {
    description
      "marking-def";
    choice marking {
      description
        "marking";
      case dscp {
        leaf mark-dscp {
          type dscp-values-type;
          description
            "mark-dscp";
        }
      }
      case precedence {
        leaf mark-precedence {
          type uint8 {
            range "0..7";
          }
          description
            "mark-precedence";
        }
      }
      case priority {
        leaf mark-priority {
          type union {
            type uint8 {
              range "1..7";
            }
            type enumeration {
              enum "ignore" {
                description
                  "ignore";
              }
            }
          }
          description
            "mark-priority";
        }
        uses marking-priority-def;
      }
    }
  }

  grouping rate-violate-def {
    description
      "rate-violate-def";
    container violate-handling {
      description
        "violate-handling";
      choice options {
        description
          "options";
        case drop-packet {
          leaf drop-packet {
            type empty;
            description
              "drop-packet";
          }
        }
        case mark-packet {
          uses marking-def;
        }
        case no-action {
          leaf no-action {
            type empty;
            description
              "no-action";
          }
        }
      }
    }
  }

  grouping rate-exceed-def {
    description
      "rate-exceed-def";
    container exceed-handling {
      description
        "exceed-handling";
      choice options {
        description
          "options";
        case drop-packet {
          leaf drop-packet {
            type empty;
            description
              "drop-packet";
          }
        }
        case mark-packet {
          uses marking-def;
        }
        case no-action {
          leaf no-action {
            type empty;
            description
              "no-action";
          }
        }
      }
    }
  }

  grouping bandwidth-rate-def {
    leaf bandwidth-rate {
      type int32 {
        range "1..2000000";
      }
      description
        "1..2000000";
      units "KBps";
    }
  }

  grouping rate-spec-packet-handling-def {
    description
      "rate-spec-packet-handling-def";
    choice rate-specifications {
      description
        "rate-specifications";
      case mark-dscp {
        leaf mark-dscp {
          type dscp-values-type;
          description
            "mark-dscp";
        }
      }
      case mark-precedence {
        leaf mark-precedence {
          type uint8 {
            range "0..7";
          }
          description
            "mark-precedence";
        }
      }
      case mark-priority {
        leaf mark-priority {
          type union {
            type uint8 {
              range "1..7";
            }
            type enumeration {
              enum "ignore" {
                description
                  "ignore";
              }
            }
          }
          description
            "mark-priority";
        }
        uses marking-priority-def;
      }
      case rate-limiting {
        container rate {
          description
            "Specify rate limits inline";
          uses rate-option-def;
          uses policy-bit-rate-def;
          container actions {
            description
              "actions";
            uses rate-conform-def;
            uses rate-exceed-def;
            uses rate-violate-def;
          }
        }
      }
    }
  }

  grouping policy-packet-handling-def {
    description
      "policy-packet-handling-def";
    container remarking {
      choice remarking-type {
        case mark-dscp {
          leaf mark-dscp {
            type dscp-values-type;
            description
              "mark-dscp";
            n-ext:maps-to "/ac:devices/ac:device/qos:policy-maps/policy-map[name=current()/../../../../../name]/class-entry[class-name=current()/../../../../class-name/name]/dscp-value";
          }
          leaf dscp-tunnel {
            type boolean;
            description
              "dscp-tunnel";
            n-ext:maps-to "/ac:devices/ac:device/qos:policy-maps/policy-map[name=current()/../../../../../name]/class-entry[class-name=current()/../../../../class-name/name]/is-dscp-tunnel";
          }
        }
        case mark-precedence {
          leaf mark-precedence {
            type uint8 {
              range "0..7";
            }
            description
              "mark-precedence";
            n-ext:maps-to "/ac:devices/ac:device/qos:policy-maps/policy-map[name=current()/../../../../../name]/class-entry[class-name=current()/../../../../class-name/name]/precedence";
          }
        }
        case mark-priority {
          leaf mark-priority {
            type union {
              type uint8 {
                range "1..7";
              }
              type enumeration {
                enum "ignore" {
                  description
                    "ignore";
                }
              }
            }
            description
              "mark-priority";
            n-ext:maps-to "/ac:devices/ac:device/qos:policy-maps/policy-map[name=current()/../../../../../name]/class-entry[class-name=current()/../../../../class-name/name]/priority-value";
          }
          uses marking-priority-def;
        }
      }
    }
    choice policy-packet-handling {
      description
        "policy-packet-handling";
      case policing {
        choice police-type {
          description
            "police-type";
          case bit-police-type {
            container police {
              description
                "police";
              uses rate-option-def;
              uses rate-spec-packet-handling-def;
              uses policy-bit-rate-def;
              leaf police-cir-percentage {
                type uint8;
                description
                  "0..255";
              }
              leaf police-cir-rate {
                type uint64 {
                  range "8000..10000000000";
                }
                description
                  "8000..10000000000";
              }
              container actions {
                description
                  "actions";
                uses rate-conform-def;
                uses rate-exceed-def;
                uses rate-violate-def;
              }
            }
          }
        }
        container priority {
          description
            "priority";
          choice priority-type {
            case priority-percent {
              uses rate-percentage-def;
            }
            case priority-level {
              leaf priority-level {
                type priority-level-def;
                description
                  "1..2";
              }
            }
            case priority-value {
              uses bandwidth-rate-def;
            }
          }
        }
      }
      case metering {
        container bandwidth {
          description
            "bandwidth";
          choice bandwidth-type {
            case percent {
              uses rate-percentage-def;
            }
            case remaining-percent {
              leaf rate-percentage {
                type percentage-def;
                description
                  "1..100";
              }
            }
            case bandwidth-rate {
              uses bandwidth-rate-def;
            }
            case bandwidth-remaining-ratio {
              leaf bandwidth-remaining-ratio {
                type uint32;
                description
                  "0..4294967295";
              }
            }
          }
          container random-detect {
            leaf random-detect {
              type random-detect-def;
              description
                "dscp-based
                 discard-class-based
                 precedence-based
                 default
                 none
                ";
            }
          }
        }
      }
      case shaping {
        container shaper {
          leaf shape-average-percent {
            type uint8 {
              range "1..100";
            }
            description
              "1..100";
          }
          leaf shape-average-bw {
            type uint64 {
              range "8000..10000000000";
            }
            description
              "8000..10000000000";
          }
          leaf bits-sustained {
            type uint64 {
              range "32..800000000";
            }
            description
              "Enter Shaper Bc Value";
          }
          leaf bits-excess {
            type uint64 {
              range "0..154400000";
            }
            description
              "Enter Shaper Be Value";
          }
        }
      }
    }
  }

  grouping hierarchical-policy-group-def {
    list policy {
      key "name";
      leaf name {
        type string-no-space;
        description
          "Enter HQoS Policy Name";
        n-ext:maps-to "/ac:devices/ac:device/qos:policy-maps/policy-map/name";
      }
      list classes {
        key "class-name";
        leaf class-name {
          type leafref {
            path "/ac:services/cpedeployment:managed-cpe-services/customer[name=current()/../../../../../name]/qos-service/class-maps/class-map/name";
            require-instance false;
          }
          description
            "Select Class-Map name";
          n-ext:maps-to "/ac:devices/ac:device/qos:policy-maps/policy-map[name=current()/../../name]/class-entry/class-name";
        }
        leaf child-qos-policy {
          type leafref {
            path "/ac:services/cpedeployment:managed-cpe-services/customer[name=current()/../../../../../name]/qos-service/policies/policy/name";
          }
          description
            "Select Child QoS Policy Name";
          n-ext:maps-to "/ac:devices/ac:device/qos:policy-maps/policy-map[name=current()/../../name]/class-entry[class-name=current()/../class-name]/service-policy";
        }
      }
    }
  }

  grouping policy-group-def {
    description
      "policy-group-def";
    list policy {
      key "name";
      leaf name {
        type string-no-space;
        description
          "name";
        n-ext:maps-to "/ac:devices/ac:device/qos:policy-maps/policy-map/name";
      }
      leaf description {
        type string;
        description
          "description";
        n-ext:maps-to "/ac:devices/ac:device/qos:policy-maps/policy-map[name=current()/../name]/description";
      }
      container classes {
        description
          "classes";
        list class-name {
          key "name";
          /*max-elements "8";*/
          description
            "class";
          leaf name {
            type leafref {
              path "/ac:services/cpedeployment:managed-cpe-services/customer[name=current()/../../../../../../name]/qos-service/class-maps/class-map/name";
              require-instance false;
            }
            n-ext:maps-to "/ac:devices/ac:device/qos:policy-maps/policy-map[name=current()/../../../name]/class-entry/class-name";
            description
              "name";
          }
          leaf class-sequence {
            type uint8 {
              range "1..32";
            }
            description
              "Enter the sequence order in which the class-map should appear within the policy-map";
          }
          container packet-handling {
            description
              "packet-handling";
            leaf parent-class {
              type string;
              description
                "parent-class";
            }
            uses policy-packet-handling-def;
          }
          container queue-limit {
            description
              "queue-limit";
            leaf queue-limit {
              type uint32;
              description
                "0..4294967295";
              n-ext:maps-to "/ac:devices/ac:device/qos:policy-maps/policy-map[name=current()/../../../../name]/class-entry[name=current()/../../name]/queue-limit/queue-limit";
            }
            leaf packets {
              type boolean;
              description
                "packets: True/False";
            }
          }
          container qos-group {
            leaf qos-group {
              type uint8 {
                range "0..99";
              }
              n-ext:maps-to "/ac:devices/ac:device/qos:policy-maps/policy-map[name=current()/../../../../name]/class-entry[name=current()/../../name]/qos-group";
              description
                "Enter QoS Group Value";
            }
          }
        }
      }
    }
  }

  grouping qos-def {
    container qos-service {
      container custom-nbar {
        list nbar-signatures {
          key "name";
          uses custom-nbar-def;
        }
      }
      //n-ext:ignore-for-brownfield;
      container class-maps {
        list class-map {
          key "name";
          leaf name {
            type string-no-space;
            description
              "Enter class-map name";
            n-ext:maps-to "/ac:devices/ac:device/qos:class-maps/class-map/name";
          }
          leaf description {
            type string {
              length "1..200";
            }
            description
              "Max Length 200 character";
            n-ext:maps-to "/ac:devices/ac:device/qos:class-maps/class-map[name=current()/../name]/description";
          }
          leaf dps {
            type boolean;
            description
              "Check if this is DPS traffic steering class-map";
          }
          uses class-map-def;
        }
      }
      container policies {
        description
          "policies";
        uses policy-group-def;
      }
      container hierarchical-policy {
        description
          "hierarchical-policy";
        uses hierarchical-policy-group-def;
      }
      container policy-update {
        n-ext:ignore-for-brownfield;
        list update-policy {
          key "name";
          leaf name {
            type string-no-space;
            description
              "string";
          }
          leaf policy-name {
            type leafref {
              path "/ac:services/cpedeployment:managed-cpe-services/customer[name=current()/../../../../name]/qos-service/policies/policy/name";
            }
            description
              "policy-name";
            mandatory true;
          }
          leaf packet-handling {
            type enumeration {
              enum "bandwidth";
              enum "priority";
            }
            description
              "bandwidth
               priority
              ";
            mandatory true;
          }
          leaf-list class {
            type leafref {
              path "/ac:services/cpedeployment:managed-cpe-services/customer[name=current()/../../../../name]/qos-service/policies/policy[name=current()/../policy-name]/classes/class-name/name";
            }
            description
              "class";
            config false;
          }
          leaf-list percentage {
            type string;
            description
              "string";
            config false;
          }
          list classes {
            key "class";
            leaf class {
              type leafref {
                path "/ac:services/cpedeployment:managed-cpe-services/customer[name=current()/../../../../../name]/qos-service/policies/policy[name=current()/../../policy-name]/classes/class-name/name";
              }
              description
                "class";
            }
            leaf percentage {
              type uint16 {
                range "0..100";
              }
              description
                "0..100";
              mandatory true;
            }
          }
          leaf single-cpe-site {
            type boolean;
            description
              "single-cpe-site: True/False";
          }
          leaf-list single-cpe-sites {
            type leafref {
              path "../../../../single-cpe-site/single-cpe-site-services/site-name";
              require-instance false;
            }
            description
              "single-sites";
            when " ../single-cpe-site = 'true' ";
          }
          leaf dual-cpe-site {
            type boolean;
            description
              "dual-cpe-site: True/False";
          }
          leaf-list dual-cpe-sites {
            type leafref {
              path "../../../../dual-cpe-site/dual-cpe-site-services/site-name";
              require-instance false;
            }
            description
              "dual-sites";
            when " ../dual-cpe-site = 'true' ";
          }
          leaf single-cpe-dual-wan-site {
            type boolean;
            description
              "single-cpe-dual-wan-site: True/False";
          }
          leaf-list single-cpe-dual-wan-sites {
            type leafref {
              path "../../../../single-cpe-dual-wan-site/single-cpe-dual-wan-site-services/site-name";
              require-instance false;
            }
            description
              "single-sites";
            when " ../single-cpe-dual-wan-site = 'true' ";
          }
          leaf dual-cpe-dual-wan-site {
            type boolean;
            description
              "dual-cpe-dual-wan-site: True/False";
          }
          leaf-list dual-cpe-dual-wan-sites {
            type leafref {
              path "../../../../dual-cpe-dual-wan-site/dual-cpe-dual-wan-site-services/site-name";
              require-instance false;
            }
            description
              "dual-sites";
            when " ../dual-cpe-dual-wan-site = 'true' ";
          }
          leaf triple-cpe-site {
            type boolean;
            description
              "triple-cpe-site: True/False";
          }
          leaf-list triple-cpe-sites {
            type leafref {
              path "../../../../triple-cpe-site/triple-cpe-site-services/site-name";
              require-instance false;
            }
            description
              "single-sites";
            when " ../triple-cpe-site = 'true' ";
          }
        }
      }
      container class-maps-update {
        n-ext:ignore-for-brownfield;
        list create-class-map {
          key "name";
          leaf name {
            type string-no-space;
            description
              "class-map name";
            //n-ext:maps-to "/ac:devices/device/qos:class-maps/class-map/name";
          }
          leaf description {
            type string {
              length "1..200";
            }
            description
              "Max Length 200 character";
            //n-ext:maps-to "/ac:devices/device/qos:class-maps/class-map/description";
          }
          leaf update-profile {
            type boolean;
            description
              "Check to update customer template";
          }
          uses class-map-def1;
          leaf apply-to-sites {
            type boolean;
            description
              "Check if you want to perform bulk update operation on individual sites";
            when "../apply-to-device-group = 'false'";
          }
          leaf apply-to-device-group {
            type boolean;
            description
              "Check if you want to perform bulk update operation on device group";
            when "../apply-to-sites = 'false'";
          }
          leaf device-group {
            type leafref {
              path "/ac:data-grouping/ac:definition/ac:name";
            }
            description
              "device-group";
            when "../apply-to-device-group = 'true'";
          }
          leaf single-cpe-site {
            type boolean;
            description
              "single-cpe-site: True/False";
            when "../apply-to-sites = 'true'";
          }
          leaf-list single-cpe-sites {
            type leafref {
              path "../../../../single-cpe-site/single-cpe-site-services/site-name";
              require-instance false;
            }
            description
              "single-sites";
            when " ../single-cpe-site = 'true' ";
          }
          leaf dual-cpe-site {
            type boolean;
            description
              "dual-cpe-site: True/False";
            when "../apply-to-sites = 'true'";
          }
          leaf-list dual-cpe-sites {
            type leafref {
              path "../../../../dual-cpe-site/dual-cpe-site-services/site-name";
              require-instance false;
            }
            description
              "dual-sites";
            when " ../dual-cpe-site = 'true' ";
          }
          leaf single-cpe-dual-wan-site {
            type boolean;
            description
              "single-cpe-dual-wan-site: True/False";
            when "../apply-to-sites = 'true'";
          }
          leaf-list single-cpe-dual-wan-sites {
            type leafref {
              path "../../../../single-cpe-dual-wan-site/single-cpe-dual-wan-site-services/site-name";
              require-instance false;
            }
            description
              "single-sites";
            when " ../single-cpe-dual-wan-site = 'true' ";
          }
          leaf dual-cpe-dual-wan-site {
            type boolean;
            description
              "dual-cpe-dual-wan-site: True/False";
            when "../apply-to-sites = 'true'";
          }
          leaf-list dual-cpe-dual-wan-sites {
            type leafref {
              path "../../../../dual-cpe-dual-wan-site/dual-cpe-dual-wan-site-services/site-name";
              require-instance false;
            }
            description
              "dual-sites";
            when " ../dual-cpe-dual-wan-site = 'true' ";
          }
          leaf triple-cpe-site {
            type boolean;
            description
              "triple-cpe-site: True/False";
            when "../apply-to-sites = 'true'";
          }
          leaf-list triple-cpe-sites {
            type leafref {
              path "../../../../triple-cpe-site/triple-cpe-site-services/site-name";
              require-instance false;
            }
            description
              "single-sites";
            when " ../triple-cpe-site = 'true' ";
          }
        }
        list update-class-map {
          key "id";
          leaf id {
            type string-no-space;
            description
              "string";
          }
          leaf name {
            type leafref {
              path "/ac:services/cpedeployment:managed-cpe-services/customer[name=current()/../../../../name]/qos-service/class-maps/class-map/name";
            }
            description
              "class-map name";
          }
          leaf description {
            type string {
              length "1..200";
            }
            description
              "Max Length 200 character";
            //n-ext:maps-to "/ac:devices/device/qos:class-maps/class-map[name=current()/../name]/description";
            config false;
          }
          leaf update-profile {
            type boolean;
            description
              "Check to update customer template";
          }
          uses class-map-def1 {
            refine "match-type" {
              config false;
            }
          }
          leaf apply-to-sites {
            type boolean;
            description
              "Check if you want to perform bulk update operation on individual sites";
            when "../apply-to-device-group = 'false'";
          }
          leaf apply-to-device-group {
            type boolean;
            description
              "Check if you want to perform bulk update operation on device group";
            when "../apply-to-sites = 'false'";
          }
          leaf device-group {
            type leafref {
              path "/ac:data-grouping/ac:definition/ac:name";
            }
            description
              "device-group";
            when "../apply-to-device-group = 'true'";
          }
          leaf single-cpe-site {
            type boolean;
            description
              "single-cpe-site: True/False";
            when "../apply-to-sites = 'true'";
          }
          leaf-list single-cpe-sites {
            type leafref {
              path "../../../../single-cpe-site/single-cpe-site-services/site-name";
              require-instance false;
            }
            description
              "single-sites";
            when " ../single-cpe-site = 'true' ";
          }
          leaf dual-cpe-site {
            type boolean;
            description
              "dual-cpe-site: True/False";
            when "../apply-to-sites = 'true'";
          }
          leaf-list dual-cpe-sites {
            type leafref {
              path "../../../../dual-cpe-site/dual-cpe-site-services/site-name";
              require-instance false;
            }
            description
              "dual-sites";
            when " ../dual-cpe-site = 'true' ";
          }
          leaf single-cpe-dual-wan-site {
            type boolean;
            description
              "single-cpe-dual-wan-site: True/False";
            when "../apply-to-sites = 'true'";
          }
          leaf-list single-cpe-dual-wan-sites {
            type leafref {
              path "../../../../single-cpe-dual-wan-site/single-cpe-dual-wan-site-services/site-name";
              require-instance false;
            }
            description
              "single-sites";
            when " ../single-cpe-dual-wan-site = 'true' ";
          }
          leaf dual-cpe-dual-wan-site {
            type boolean;
            description
              "dual-cpe-dual-wan-site: True/False";
            when "../apply-to-sites = 'true'";
          }
          leaf-list dual-cpe-dual-wan-sites {
            type leafref {
              path "../../../../dual-cpe-dual-wan-site/dual-cpe-dual-wan-site-services/site-name";
              require-instance false;
            }
            description
              "dual-sites";
            when " ../dual-cpe-dual-wan-site = 'true' ";
          }
          leaf triple-cpe-site {
            type boolean;
            description
              "triple-cpe-site: True/False";
            when "../apply-to-sites = 'true'";
          }
          leaf-list triple-cpe-sites {
            type leafref {
              path "../../../../triple-cpe-site/triple-cpe-site-services/site-name";
              require-instance false;
            }
            description
              "single-sites";
            when " ../triple-cpe-site = 'true' ";
          }
        }
        list delete-class-map {
          key "id";
          leaf id {
            type string-no-space;
            description
              "string";
          }
          leaf name {
            type leafref {
              path "/ac:services/cpedeployment:managed-cpe-services/customer[name=current()/../../../../name]/qos-service/class-maps/class-map/name";
            }
            description
              "class-map name";
          }
          leaf description {
            type string {
              length "1..200";
            }
            description
              "Max Length 200 character";
            //n-ext:maps-to "/ac:devices/device/qos:class-maps/class-map[name=current()/../name]/description";
            config false;
          }
          leaf update-profile {
            type boolean;
            description
              "Check to update customer template";
          }
          uses class-map-def1 {
            refine "match-type" {
              config false;
            }
          }
          leaf apply-to-sites {
            type boolean;
            description
              "Check if you want to perform bulk update operation on individual sites";
            when "../apply-to-device-group = 'false'";
          }
          leaf apply-to-device-group {
            type boolean;
            description
              "Check if you want to perform bulk update operation on device group";
            when "../apply-to-sites = 'false'";
          }
          leaf device-group {
            type leafref {
              path "/ac:data-grouping/ac:definition/ac:name";
            }
            description
              "device-group";
            when "../apply-to-device-group = 'true'";
          }
          leaf single-cpe-site {
            type boolean;
            description
              "single-cpe-site: True/False";
            when "../apply-to-sites = 'true'";
          }
          leaf-list single-cpe-sites {
            type leafref {
              path "../../../../single-cpe-site/single-cpe-site-services/site-name";
              require-instance false;
            }
            description
              "single-sites";
            when " ../single-cpe-site = 'true' ";
          }
          leaf dual-cpe-site {
            type boolean;
            description
              "dual-cpe-site: True/False";
            when "../apply-to-sites = 'true'";
          }
          leaf-list dual-cpe-sites {
            type leafref {
              path "../../../../dual-cpe-site/dual-cpe-site-services/site-name";
              require-instance false;
            }
            description
              "dual-sites";
            when " ../dual-cpe-site = 'true' ";
          }
          leaf single-cpe-dual-wan-site {
            type boolean;
            description
              "single-cpe-dual-wan-site: True/False";
            when "../apply-to-sites = 'true'";
          }
          leaf-list single-cpe-dual-wan-sites {
            type leafref {
              path "../../../../single-cpe-dual-wan-site/single-cpe-dual-wan-site-services/site-name";
              require-instance false;
            }
            description
              "single-sites";
            when " ../single-cpe-dual-wan-site = 'true' ";
          }
          leaf dual-cpe-dual-wan-site {
            type boolean;
            description
              "dual-cpe-dual-wan-site: True/False";
            when "../apply-to-sites = 'true'";
          }
          leaf-list dual-cpe-dual-wan-sites {
            type leafref {
              path "../../../../dual-cpe-dual-wan-site/dual-cpe-dual-wan-site-services/site-name";
              require-instance false;
            }
            description
              "dual-sites";
            when " ../dual-cpe-dual-wan-site = 'true' ";
          }
          leaf triple-cpe-site {
            type boolean;
            description
              "triple-cpe-site: True/False";
            when "../apply-to-sites = 'true'";
          }
          leaf-list triple-cpe-sites {
            type leafref {
              path "../../../../triple-cpe-site/triple-cpe-site-services/site-name";
              require-instance false;
            }
            description
              "single-sites";
            when " ../triple-cpe-site = 'true' ";
          }
        }
      }
      container policy-class-map-update {
        n-ext:ignore-for-brownfield;
        list update-policy-class-map {
          key "name";
          leaf name {
            type string-no-space;
            description
              "string";
          }
          leaf policy-name {
            type leafref {
              path "/ac:services/cpedeployment:managed-cpe-services/customer[name=current()/../../../../name]/qos-service/policies/policy/name";
            }
            description
              "policy-name";
            mandatory true;
          }
          leaf update-profile {
            type boolean;
            description
              "Check to update customer template";
          }
          leaf class {
            type leafref {
              path "/ac:services/cpedeployment:managed-cpe-services/customer[name=current()/../../../../name]/qos-service/class-maps-update/create-class-map/name";
            }
            description
              "class";
            mandatory true;
          }
          leaf packet-handling {
            type enumeration {
              enum "bandwidth";
              enum "priority";
            }
            description
              "bandwidth
               priority
              ";
            mandatory true;
          }
          leaf percentage {
            type uint16 {
              range "0..100";
            }
            description
              "0..100";
            mandatory true;
          }
          leaf queue-limit {
            type uint32;
            description
              "0..4294967295";
          }
          leaf packets {
            type boolean;
            description
              "packets: True/False";
          }
          leaf qos-group {
            type uint8 {
              range "0..99";
            }
            description
              "Enter QoS Group Value";
          }
          leaf apply-to-sites {
            type boolean;
            description
              "Check if you want to perform bulk update operation on individual sites";
            when "../apply-to-device-group = 'false'";
          }
          leaf apply-to-device-group {
            type boolean;
            description
              "Check if you want to perform bulk update operation on device group";
            when "../apply-to-sites = 'false'";
          }
          leaf device-group {
            type leafref {
              path "/ac:data-grouping/ac:definition/ac:name";
            }
            description
              "device-group";
            when "../apply-to-device-group = 'true'";
          }
          leaf single-cpe-site {
            type boolean;
            description
              "single-cpe-site: True/False";
            when "../apply-to-sites = 'true'";
          }
          leaf-list single-cpe-sites {
            type leafref {
              path "../../../../single-cpe-site/single-cpe-site-services/site-name";
              require-instance false;
            }
            description
              "single-sites";
            when " ../single-cpe-site = 'true' ";
          }
          leaf dual-cpe-site {
            type boolean;
            description
              "dual-cpe-site: True/False";
            when "../apply-to-sites = 'true'";
          }
          leaf-list dual-cpe-sites {
            type leafref {
              path "../../../../dual-cpe-site/dual-cpe-site-services/site-name";
              require-instance false;
            }
            description
              "dual-sites";
            when " ../dual-cpe-site = 'true' ";
          }
          leaf single-cpe-dual-wan-site {
            type boolean;
            description
              "single-cpe-dual-wan-site: True/False";
            when "../apply-to-sites = 'true'";
          }
          leaf-list single-cpe-dual-wan-sites {
            type leafref {
              path "../../../../single-cpe-dual-wan-site/single-cpe-dual-wan-site-services/site-name";
              require-instance false;
            }
            description
              "single-sites";
            when " ../single-cpe-dual-wan-site = 'true' ";
          }
          leaf dual-cpe-dual-wan-site {
            type boolean;
            description
              "dual-cpe-dual-wan-site: True/False";
            when "../apply-to-sites = 'true'";
          }
          leaf-list dual-cpe-dual-wan-sites {
            type leafref {
              path "../../../../dual-cpe-dual-wan-site/dual-cpe-dual-wan-site-services/site-name";
              require-instance false;
            }
            description
              "dual-sites";
            when " ../dual-cpe-dual-wan-site = 'true' ";
          }
          leaf triple-cpe-site {
            type boolean;
            description
              "triple-cpe-site: True/False";
            when "../apply-to-sites = 'true'";
          }
          leaf-list triple-cpe-sites {
            type leafref {
              path "../../../../triple-cpe-site/triple-cpe-site-services/site-name";
              require-instance false;
            }
            description
              "single-sites";
            when " ../triple-cpe-site = 'true' ";
          }
        }
      }
    }
  }

  grouping class-map-def1 {
    description
      "class-map grouping";
    leaf match-type {
      type match-type-def;
      description
        "match-all
         match-any
        ";
      default "match-any";
    }
    leaf-list dscp {
      type dscp-values-type;
      description
        "Select DSCP Value(s) to match";
    }
    leaf-list access-group {
      type leafref {
        path "/ac:services/cpedeployment:managed-cpe-services/customer[name=current()/../../../../name]/access-lists/access-list/name";
        require-instance false;
      }
      description
        "Select ACL to match";
    }
    leaf-list qos-group {
      type qos-group-def;
      //type uint8 {
      //range "0..99";
      //}
      description
        "Select QoS Group Value(s) to match";
    }
    leaf-list protocol {
      type protocol-def;
      description
        "Select NBAR Signature(s) to match";
    }
    leaf-list custom-nbar {
      type leafref {
        path "/ac:services/cpedeployment:managed-cpe-services/customer[name=current()/../../../../name]/qos-service/custom-nbar/nbar-signatures/name";
        require-instance false;
      }
      description
        "Select Custom NBAR Signatures to match";
    }
    leaf-list http-url {
      type string-no-space;
      description
        "Enter HTTP URL to match";
    }
  }

  grouping class-map-def {
    description
      "class-map grouping";
    leaf match-type {
      type match-type-def;
      description
        "match-all
         match-any
        ";
      default "match-any";
      n-ext:maps-to "/ac:devices/ac:device/qos:class-maps/class-map[name=current()/../name]/match-type";
      //      n-ext:maps-to "/ac:devices/device/qos:class-maps/class-map/class-match-condition/match-type";
    }
    leaf-list dscp {
      type dscp-values-type;
      description
        "Union Input types:
         enumeration
        ";
      n-ext:maps-to "/ac:devices/ac:device/qos:class-maps/class-map[name=current()/../name]/class-match-condition[condition-type=dscp]/match-value";
    }
    leaf-list access-group {
      type leafref {
        path "/ac:services/cpedeployment:managed-cpe-services/customer[name=current()/../../../../name]/access-lists/access-list/name";
        require-instance false;
      }
      description
        "access-group";
      n-ext:maps-to "/ac:devices/ac:device/qos:class-maps/class-map[name=current()/../name]/class-match-condition[condition-type=access-group]/match-value";
    }
    leaf-list qos-group {
      type qos-group-def;
      //type uint8 {
      //range "0..99";
      //}
      description
        "Enter QoS Group Value";
      n-ext:maps-to "/ac:devices/ac:device/qos:class-maps/class-map[name=current()/../name]/class-match-condition[condition-type=qos-group]/match-value";
    }
    leaf-list protocol {
      type protocol-def;
      description
        "Select NBAR Signature(s)";
      n-ext:maps-to "/ac:devices/ac:device/qos:class-maps/class-map[name=current()/../name]/class-match-condition[condition-type=protocol]/match-value";
    }
    leaf-list custom-nbar {
      type leafref {
        path "/ac:services/cpedeployment:managed-cpe-services/customer[name=current()/../../../../name]/qos-service/custom-nbar/nbar-signatures/name";
        require-instance false;
      }
      description
        "Select Custom NBAR Signatures to match";
    }
    leaf-list http-url {
      type string-no-space;
      description
        "string";
      n-ext:maps-to "/ac:devices/ac:device/qos:class-maps/class-map[name=current()/../name]/class-match-condition/http-url/url";
    }
    /*leaf traffic-class {
      type boolean;
      description
        "traffic-class: True/False";
    }
    leaf protocol-attribute {
      type traffic-class-def;
      description
        "broadcast-video
         bulk-data
         multimedia-conferencing
         multimedia-streaming
         network-control
         ops-admin-mgmt
         real-time-interactive
         signaling
         transactional-data
         voip-telephony
        ";
      when " ../traffic-class = 'true' ";
    }
    leaf business-relevance {
      type boolean;
      description
        "business-relevance: True/False";
      default "true";
      when " ../traffic-class = 'true' ";
    }
    leaf pre-configured {
      type boolean;
      description
        "pre-configured: True/False";
    }*/
  }

  grouping route-maps-def-list {
    list route-map {
      key "route-map-name";
      leaf route-map-name {
        /*type string;*/
        description
          "route-map-name";
        type leafref {
          //path "../../../../../../route-maps/route-map/route-map-name";
          path "/ac:services/cpedeployment:managed-cpe-services/customer[name=current()/../../../../../../name]/route-maps/route-map/route-map-name";
        }
        n-ext:maps-to "/ac:devices/ac:device[ac:id=current()/../../../device-ip]/l3:route-maps/route-map/name";
      }
      leaf sequence-number {
        type string;
        default "14";
        description
          "sequence-number";
        config false;
      }
    }
  }

  grouping dps-route-maps-def-list {
    list route-map {
      key "route-map-name";
      leaf route-map-name {
        /*type string;*/
        description
          "route-map-name";
        type leafref {
          //path "../../../../../../route-maps/route-map/route-map-name";
          path "/ac:services/cpedeployment:managed-cpe-services/customer[name=current()/../../../../../../name]/route-maps/route-map/route-map-name";
        }
        n-ext:maps-to "/ac:devices/ac:device/l3:route-maps/route-map/name";
      }
      leaf sequence-number {
        type string;
        default "12";
        description
          "sequence-number";
        config false;
      }
    }
  }

  grouping community-lists-ref-def {
    list community-list {
      key "community-list-name";
      leaf community-list-name {
        /*type string;*/
        description
          "community-list-name";
        type leafref {
          //path "../../../../../../community-lists/community-list/community-list-name";
          path "/ac:services/cpedeployment:managed-cpe-services/customer[name=current()/../../../../../../name]/community-lists/community-list/community-list-name";
        }
        n-ext:maps-to "/ac:devices/ac:device[ac:id=current()/../../../device-ip]/l3:community-lists/community-list/community-list-name";
      }
      leaf sequence-number {
        type string;
        default "16";
        description
          "sequence-number";
        config false;
      }
    }
  }

  grouping extcommunity-lists-ref-def {
    list extcommunity-list {
      key "extcommunity-list-name";
      leaf extcommunity-list-name {
        type string-no-space;
        description
          "extcommunity-list-name";
        //type leafref {
        //  path "../../../../../../extcommunity-lists/extcommunity-list/extcommunity-list-name";
        //}
      }
      leaf sequence-number {
        type string;
        default "5";
        description
          "sequence-number";
        config false;
      }
    }
  }

  grouping vrf-list-def {
    list vrf {
      key "name";
      leaf sequence-number {
        type string;
        default "3";
        description
          "sequence-number";
        config false;
      }
      leaf name {
        type string-no-space;
        description
          "string";
      }
      leaf vrf-name {
        description
          "name";
        type leafref {
          // path "../../../../../../vrfs/vrf/vrf-name";
          path "/ac:services/cpedeployment:managed-cpe-services/customer[name=current()/../../../../../../name]/vrfs/vrf/vrf-name";
        }
        n-ext:maps-to "/ac:devices/ac:device[ac:id=current()/../../../device-ip]/l3:vrfs/vrf/name";
      }
      leaf bgp-settings {
        description
          "Check if BGP config is required under this VRF";
        type boolean;
        default "true";
      }
      leaf bgp-router-id {
        type inet:ipv4-address;
        description
          "BGP Router-ID";
        n-ext:maps-to "/ac:devices/ac:device[ac:id=current()/../../../device-ip]/l3:vrfs/vrf[name=current()/../vrf-name]/router-bgp/router-id";
        when " ../bgp-settings = 'true' ";
      }
      leaf bgp-address-family {
        type enumeration {
          enum "ipv4";
          enum "ipv4-vpn4";
          enum "vpnv4";
          enum "ipv6";
        }
        n-ext:maps-to "/ac:devices/ac:device[ac:id=current()/../../../device-ip]/l3:vrfs/vrf[name=current()/../vrf-name]/router-bgp/address-family";
        description
          "ipv4
           ipv4-vpn4
           vpnv4
           ipv6
          ";
        when " ../bgp-settings = 'true' ";
      }
      leaf default-information-originate {
        type boolean;
        description
          "default-information-originate: True/False";
        n-ext:maps-to "/ac:devices/ac:device[ac:id=current()/../../../device-ip]/l3:vrfs/vrf[name=current()/../vrf-name]/router-bgp/default-information-originate";
        when " ../bgp-settings = 'true' ";
      }
      leaf bgp-distance {
        type boolean;
        description
          "Check to change default BGP Routes Administrative Distance";
        when " ../bgp-settings = 'true' ";
      }
      leaf bgp-distance-external {
        type uint8;
        description
          "Enter BGP Distance for External Routes";
        n-ext:maps-to "/ac:devices/ac:device[ac:id=current()/../../../device-ip]/l3:vrfs/vrf[name=current()/../vrf-name]/router-bgp/eroutes";
        when " ../bgp-distance = 'true' ";
      }
      leaf bgp-distance-internal {
        type uint8;
        description
          "Enter BGP Distance for Internal Routes";
        n-ext:maps-to "/ac:devices/device[ac:id=current()/../../../device-ip]/l3:vrfs/vrf[name=current()/../vrf-name]/router-bgp/iroutes";
        when " ../bgp-distance = 'true' ";
      }
      leaf bgp-distance-local {
        type uint8;
        description
          "Enter BGP Distance for Local Routes";
        n-ext:maps-to "/ac:devices/device[ac:id=current()/../../../device-ip]/l3:vrfs/vrf[name=current()/../vrf-name]/router-bgp/lroutes";
        when " ../bgp-distance = 'true' ";
      }
      leaf bgp-redis-internal {
        type boolean;
        description
          "iBGP Routes Redistribution: True/False";
        n-ext:maps-to "/ac:devices/device[ac:id=current()/../../../device-ip]/l3:vrfs/vrf[name=current()/../vrf-name]/router-bgp/redistribute-internal";
        when " ../bgp-settings = 'true' ";
      }
      leaf bgp-keepalive-timer {
        type uint16 {
          range "0..65535";
        }
        description
          "0..65535";
        n-ext:maps-to "/ac:devices/ac:device[ac:id=current()/../../../device-ip]/l3:vrfs/vrf[name=current()/../vrf-name]/router-bgp/bgp-keepalive-timer";
        when " ../bgp-settings = 'true' ";
      }
      leaf bgp-holdtime-timer {
        type uint16 {
          range "0..65535";
        }
        description
          "0..65535";
        n-ext:maps-to "/ac:devices/ac:device[ac:id=current()/../../../device-ip]/l3:vrfs/vrf[name=current()/../vrf-name]/router-bgp/bgp-holdtime-timer";
        when " ../bgp-settings = 'true' ";
      }
      uses bgp-def;
      leaf redistribute-connected {
        type boolean;
        description
          "redistribute-connected: True/False";
        //default "true";
        //n-ext:maps-to "/ac:devices/ac:device[id=current()/../../../device-ip]/l3:vrfs/vrf[name=current()/../vrf-name]/router-bgp/redistribute/redistribute-connected";
        when " ../bgp-settings = 'true' ";
      }
      leaf redistribute-connected-route-policy {
        type leafref {
          //path "../../../../../../route-maps/route-map/route-map-name";
          path "/ac:services/cpedeployment:managed-cpe-services/customer[name=current()/../../../../../../name]/route-maps/route-map/route-map-name";
        }
        //n-ext:maps-to "/ac:devices/device[id=current()/../../../device-ip]/l3:route-maps/route-map/name";
        n-ext:maps-to "/ac:devices/ac:device[ac:id=current()/../../../device-ip]/l3:vrfs/vrf[name=current()/../vrf-name]/router-bgp/redistribute[protocol=connected]/route-map";
        description
          "redistribute-connected-route-policy";
        when " ../redistribute-connected = 'true'";
      }
      leaf redistribute-static {
        type boolean;
        description
          "redistribute-static: True/False";
        when " ../bgp-settings = 'true' ";
      }
      leaf redistribute-static-route-policy {
        type leafref {
          //path "../../../../../../route-maps/route-map/route-map-name";
          path "/ac:services/cpedeployment:managed-cpe-services/customer[name=current()/../../../../../../name]/route-maps/route-map/route-map-name";
        }
        //n-ext:maps-to "/ac:devices/device[id=current()/../../../device-ip]/l3:route-maps/route-map/name";
        n-ext:maps-to "/ac:devices/ac:device[ac:id=current()/../../../device-ip]/l3:vrfs/vrf[name=current()/../vrf-name]/router-bgp/redistribute[protocol=static]/route-map";
        description
          "redistribute-static-route-policy";
        when " ../redistribute-static = 'true'";
      }
      leaf aggregate-summary-networks {
        type boolean;
        description
          "aggregate-summary-networks: True/False";
        //n-ext:maps-to "/ac:devices/ac:device[id=current()/../../../device-ip]/l3:vrfs/vrf[name=current()/../vrf-name]/router-bgp/aggregate-summary-network";
        when " ../bgp-settings = 'true'";
      }
      leaf summary-networks {
        type string;
        description
          "string";
        when " ../aggregate-summary-networks = 'true'";
        n-ext:maps-to "/ac:devices/ac:device[ac:id=current()/../../../device-ip]/l3:vrfs/vrf[name=current()/../vrf-name]/router-bgp/aggregate-summary-network/network";
      }
      list interface {
        key "sequence-number";
        //key "entry-sequence-number";
        leaf sequence-number {
          type uint8 {
            range "101..120";
          }
          default "101";
          description
            "sequence-number: This is NCX internal reference. By default 101 is the value, in case if any key issues value can be changed";
        }
        leaf entry-sequence-number {
          type leafref {
            path "/ac:services/cpedeployment:managed-cpe-services/customer[name=current()/../../../../../../../name]/route-maps/route-map[route-map-name=current()/../../redistribute-connected-route-policy]/route-map-entries/sequence-number";
          }
          n-ext:maps-to "/ac:devices/ac:device[ac:id=current()/../../../../device-ip]/l3:route-maps/route-map[name=current()/../../redistribute-connected-route-policy]/route-map-entries/seq";
          description
            "Enter the Route-Map entry Sequence Number containing the LAN-INTERFACE keyword";
        }
        leaf interface-name {
          type union {
            type leafref {
              path "/ac:devices/ac:device[ac:id=current()/../../../../device-ip]/if:interfaces/if:interface/if:name";
              require-instance false;
            }
            type string-no-lead-trail-space;
          }
          //n-ext:maps-to "/ac:devices/device[id=current()/../../../../device-ip]/if:interfaces/if:interface[vrf=current()/../../vrf-name]/if:name";
          //n-ext:maps-to "/ac:devices/device[id=current()/../../../../device-ip]/if:interfaces/if:interface[l3:vrf=current()/../../vrf-name]/if:name";
          //n-ext:maps-to "/ac:devices/device[id=current()/../../../../device-ip]/if:interfaces/if:interface/if:name";
          n-ext:maps-to "/ac:devices/ac:device[ac:id=current()/../../../../device-ip]/l3:route-maps/route-map[name=current()/../../redistribute-connected-route-policy]/route-map-entries[seq=current()/../entry-sequence-number]/match-condition[condition-type=interface]/value";
          description
            "Enter the Interface(s) to redistribute.
             If multiple interfaces are specified, separate them with a space";
        }
      }
    }
  }

  grouping class-maps-def-list {
    list class-map {
      key "name";
      leaf name {
        /*type string;*/
        description
          "Select Class-Map Name";
        type leafref {
          //path "../../../../../../qos-service/class-maps/class-map/name";
          path "/ac:services/cpedeployment:managed-cpe-services/customer[name=current()/../../../../../../name]/qos-service/class-maps/class-map/name";
        }
        n-ext:maps-to "/ac:devices/ac:device[ac:id=current()/../../../device-ip]/qos:class-maps/qos:class-map/qos:name";
        mandatory true;
      }
      leaf-list access-list {
        type string;
        description
          "Select ACL to match";
        n-ext:maps-to "/ac:devices/ac:device[ac:id=current()/../../../device-ip]/acl:access-lists/acl:access-list/acl:name";
        //mandatory true;
      }
      leaf sequence-number {
        type string;
        default "27";
        description
          "sequence-number";
        config false;
      }
    }
  }

  grouping prefix-lists-def-list {
    list prefix-list {
      key "prefix-list-name";
      leaf prefix-list-name {
        /*type string;*/
        description
          "prefix-list-name";
        type leafref {
          //path "../../../../../../prefix-lists/prefix-list/prefix-list-name";
          path "/ac:services/cpedeployment:managed-cpe-services/customer[name=current()/../../../../../../name]/prefix-lists/prefix-list/prefix-list-name";
        }
        n-ext:maps-to "/ac:devices/ac:device[ac:id=current()/../../../device-ip]/l3features:ip-prefixlist-list/ip-prefixlist/name";
      }
      leaf sequence-number {
        type string;
        default "18";
        description
          "sequence-number";
        config false;
      }
    }
  }

  grouping dps-prefix-lists-def-list {
    list prefix-list {
      key "prefix-list-name";
      leaf prefix-list-name {
        /*type string;*/
        description
          "prefix-list-name";
        type leafref {
          //path "../../../../../../prefix-lists/prefix-list/prefix-list-name";
          path "/ac:services/cpedeployment:managed-cpe-services/customer[name=current()/../../../../../../name]/prefix-lists/prefix-list/prefix-list-name";
        }
        n-ext:maps-to "/ac:devices/ac:device/l3features:ip-prefixlist-list/ip-prefixlist/name";
      }
      leaf sequence-number {
        type string;
        default "16";
        description
          "sequence-number";
        config false;
      }
    }
  }

  grouping route-maps-def {
    container route-maps {
      //n-ext:ignore-for-brownfield;
      list route-map {
        key "route-map-name";
        /*leaf ncx-unique-name {
          type string;
          description
            "string";
        }*/
        leaf route-map-name {
          type string-no-space;
          description
            "string";
          n-ext:maps-to "/ac:devices/ac:device/l3:route-maps/route-map/name";
        }
        leaf description {
          type string;
          description
            "string";
        }
        list route-map-entries {
          key "sequence-number";
          leaf sequence-number {
            type uint16 {
              range "0..65535";
            }
            description
              "0..65535";
            n-ext:maps-to "/ac:devices/ac:device/l3:route-maps/route-map[name=current()/../../route-map-name]/route-map-entries/seq";
          }
          leaf description {
            type string;
            description
              "string";
            n-ext:maps-to "/ac:devices/ac:device/l3:route-maps/route-map[name=current()/../../route-map-name]/route-map-entries[seq=current()/../sequence-number]/description";
          }
          leaf action {
            type action-type;
            description
              "permit
               deny
              ";
            n-ext:maps-to "/ac:devices/ac:device/l3:route-maps/route-map[name=current()/../../route-map-name]/route-map-entries[seq=current()/../sequence-number]/action";
          }
          leaf continue {
            type uint16 {
              range "0..65535";
            }
            description
              "0..65535";
            //n-ext:maps-to "/ac:devices/device/l3:route-maps/route-map[name=current()/../../route-map-name]/route-map-entries[seq=current()/../sequence-number]/action";
          }
          list match-condition {
            key "condition-type value";
            leaf condition-type {
              type route-map-condition-types;
              description
                "interface
                 tag
                 acl
                 prefix-list
                 source-protocol
                 community
                 metric
                 as-path
                 next-hop
                ";
              n-ext:maps-to "/ac:devices/ac:device/l3:route-maps/route-map[name=current()/../../../route-map-name]/route-map-entries[seq=current()/../../route-map-entries/sequence-number]/match-condition/condition-type";
            }
            leaf value {
              type string-no-lead-trail-space;
              description
                "string";
              n-ext:maps-to "/ac:devices/ac:device/l3:route-maps/route-map[name=current()/../../../route-map-name]/route-map-entries[seq=current()/../../route-map-entries/sequence-number]/match-condition/value";
            }
          }
          list set-action {
            key "set-type value";
            leaf set-type {
              type route-map-set-types;
              description
                "local-preference
                 metric
                 as-path
                 tag
                 community
                 next-hop
                 as-path prepend
                ";
              n-ext:maps-to "/ac:devices/ac:device/l3:route-maps/route-map[name=current()/../../../route-map-name]/route-map-entries[seq=current()/../../route-map-entries/sequence-number]/set-action/set-type";
            }
            leaf ip {
              type ip-types;
              description
                "precedence
                 next-hop
                 df
                ";
              when " ../set-type = 'ip' ";
              n-ext:maps-to "/ac:devices/ac:device/l3:route-maps/route-map[name=current()/../../../route-map-name]/route-map-entries[seq=current()/../../route-map-entries/sequence-number]/set-action/ip";
            }
            leaf value {
              type string-no-lead-trail-space;
              description
                "string";
              n-ext:maps-to "/ac:devices/ac:device/l3:route-maps/route-map[name=current()/../../../route-map-name]/route-map-entries[seq=current()/../../route-map-entries/sequence-number]/set-action/value";
            }
          }
        }
      }
      list update-route-maps {
        n-ext:ignore-for-brownfield;
        key "id";
        leaf id {
          type string-no-space;
          description
            "Enter Transaction Name
             This is an internal field for Anuta NCX
            ";
        }
        leaf route-map-name {
          type leafref {
            path "/ac:services/cpedeployment:managed-cpe-services/customer[name=current()/../../../name]/route-maps/route-map/route-map-name";
          }
          description
            "route-map-name";
          mandatory true;
        }
        leaf update-profile {
          type boolean;
          description
            "Check to update customer template";
        }
        leaf sequence-number {
          type union {
            type leafref {
              path "/ac:services/cpedeployment:managed-cpe-services/customer[name=current()/../../../name]/route-maps/route-map[route-map-name=current()/../route-map-name]/route-map-entries/sequence-number";
            }
            type uint16 {
              range "1..65535";
            }
          }
          description
            "sequence-number";
          mandatory true;
        }
        leaf action {
          type union {
            type leafref {
              path "/ac:services/cpedeployment:managed-cpe-services/customer[name=current()/../../../name]/route-maps/route-map[route-map-name=current()/../route-map-name]/route-map-entries[sequence-number=current()/../sequence-number]/action";
            }
            type string-no-space;
          }
          description
            "Enter Route-Map Sequence Action: Permit/Deny";
          mandatory true;
        }
        leaf entry {
          type enumeration {
            enum "match-condition";
            enum "set-action";
          }
          description
            "match-condition
             set-action
            ";
          mandatory true;
        }
        leaf condition-type {
          type route-map-condition-types;
          description
            "interface
             tag
             acl
             prefix-list
             source-protocol
             community
             metric
             as-path
             next-hop
             address
            ";
          when " ../entry = 'match-condition' ";
        }
        leaf value {
          type string-no-lead-trail-space;
          description
            "string";
          when " ../entry = 'match-condition' ";
        }
        leaf set-type {
          type route-map-set-types;
          description
            "local-preference
             metric
             as-path
             tag
             community
             next-hop
             as-path prepend
             vrf
             ip
            ";
          when " ../entry = 'set-action' ";
        }
        leaf ip {
          type ip-types;
          description
            "precedence
             next-hop
             df
            ";
          when " ../set-type = 'ip' and ../entry = 'set-action'";
        }
        leaf set-value {
          type string-no-lead-trail-space;
          description
            "string";
          when " ../entry = 'set-action' ";
        }
        leaf apply-to-sites {
          type boolean;
          description
            "Check if you want to perform bulk update operation on individual sites";
          when "../apply-to-device-group = 'false'";
        }
        leaf apply-to-device-group {
          type boolean;
          description
            "Check if you want to perform bulk update operation on device group";
          when "../apply-to-sites = 'false'";
        }
        leaf device-group {
          type leafref {
            path "/ac:data-grouping/ac:definition/ac:name";
          }
          description
            "device-group";
          when "../apply-to-device-group = 'true'";
        }
        leaf single-cpe-site {
          type boolean;
          description
            "single-cpe-site: True/False";
          when "../apply-to-sites = 'true'";
        }
        leaf-list single-cpe-sites {
          type leafref {
            path "../../../single-cpe-site/single-cpe-site-services/site-name";
            require-instance false;
          }
          description
            "single-sites";
          when " ../single-cpe-site = 'true' ";
        }
        leaf dual-cpe-site {
          type boolean;
          description
            "dual-cpe-site: True/False";
          when "../apply-to-sites = 'true'";
        }
        leaf-list dual-cpe-sites {
          type leafref {
            path "../../../dual-cpe-site/dual-cpe-site-services/site-name";
            require-instance false;
          }
          description
            "dual-sites";
          when " ../dual-cpe-site = 'true' ";
        }
        leaf single-cpe-dual-wan-site {
          type boolean;
          description
            "single-cpe-dual-wan-site: True/False";
          when "../apply-to-sites = 'true'";
        }
        leaf-list single-cpe-dual-wan-sites {
          type leafref {
            path "../../../single-cpe-dual-wan-site/single-cpe-dual-wan-site-services/site-name";
            require-instance false;
          }
          description
            "single-sites";
          when " ../single-cpe-dual-wan-site = 'true' ";
        }
        leaf dual-cpe-dual-wan-site {
          type boolean;
          description
            "dual-cpe-dual-wan-site: True/False";
          when "../apply-to-sites = 'true'";
        }
        leaf-list dual-cpe-dual-wan-sites {
          type leafref {
            path "../../../dual-cpe-dual-wan-site/dual-cpe-dual-wan-site-services/site-name";
            require-instance false;
          }
          description
            "dual-sites";
          when " ../dual-cpe-dual-wan-site = 'true' ";
        }
        leaf triple-cpe-site {
          type boolean;
          description
            "triple-cpe-site: True/False";
          when "../apply-to-sites = 'true'";
        }
        leaf-list triple-cpe-sites {
          type leafref {
            path "../../../triple-cpe-site/triple-cpe-site-services/site-name";
            require-instance false;
          }
          description
            "single-sites";
          when " ../triple-cpe-site = 'true' ";
        }
      }
      list delete-route-maps {
        n-ext:ignore-for-brownfield;
        key "id";
        leaf id {
          type string-no-space;
          description
            "Enter Transaction ID
             This is an internal field for Anuta NCX
            ";
        }
        leaf route-map-name {
          type leafref {
            path "/ac:services/cpedeployment:managed-cpe-services/customer[name=current()/../../../name]/route-maps/route-map/route-map-name";
          }
          description
            "route-map-name";
          mandatory true;
        }
        leaf sequence-number {
          type leafref {
            path "/ac:services/cpedeployment:managed-cpe-services/customer[name=current()/../../../name]/route-maps/route-map[route-map-name=current()/../route-map-name]/route-map-entries/sequence-number";
          }
          description
            "sequence-number";
          mandatory true;
        }
        leaf update-profile {
          type boolean;
          description
            "Check to update customer template";
        }
        leaf action {
          type leafref {
            path "/ac:services/cpedeployment:managed-cpe-services/customer[name=current()/../../../name]/route-maps/route-map[route-map-name=current()/../route-map-name]/route-map-entries[sequence-number=current()/../sequence-number]/action";
          }
          description
            "action";
          mandatory true;
        }
        leaf entry {
          type enumeration {
            enum "match-condition";
            enum "set-action";
            enum "delete-sequence-entry";
          }
          description
            "Select Entry condition
             NOTE: delete-sequency-entry will delete the entire route-map sequence entry
            ";
          mandatory true;
        }
        leaf condition-type {
          type route-map-condition-types;
          description
            "interface
             tag
             acl
             prefix-list
             source-protocol
             community
             metric
             as-path
             next-hop
             address
            ";
          when " ../entry = 'match-condition' ";
        }
        leaf value {
          type string-no-lead-trail-space;
          description
            "string";
          when " ../entry = 'match-condition' ";
        }
        leaf set-type {
          type route-map-set-types;
          description
            "local-preference
             metric
             as-path
             tag
             community
             next-hop
             as-path prepend
             vrf
             ip
            ";
          when " ../entry = 'set-action' ";
        }
        leaf ip {
          type ip-types;
          description
            "precedence
             next-hop
             df
            ";
          when " ../set-type = 'ip' and ../entry = 'set-action'";
        }
        leaf set-value {
          type string-no-lead-trail-space;
          description
            "string";
          when " ../entry = 'set-action' ";
        }
        leaf apply-to-sites {
          type boolean;
          description
            "Check if you want to perform bulk update operation on individual sites";
          when "../apply-to-device-group = 'false'";
        }
        leaf apply-to-device-group {
          type boolean;
          description
            "Check if you want to perform bulk update operation on device group";
          when "../apply-to-sites = 'false'";
        }
        leaf device-group {
          type leafref {
            path "/ac:data-grouping/ac:definition/ac:name";
          }
          description
            "device-group";
          when "../apply-to-device-group = 'true'";
        }
        leaf single-cpe-site {
          type boolean;
          description
            "single-cpe-site: True/False";
          when "../apply-to-sites = 'true'";
        }
        leaf-list single-cpe-sites {
          type leafref {
            path "../../../single-cpe-site/single-cpe-site-services/site-name";
            require-instance false;
          }
          description
            "single-sites";
          when " ../single-cpe-site = 'true' ";
        }
        leaf dual-cpe-site {
          type boolean;
          description
            "dual-cpe-site: True/False";
          when "../apply-to-sites = 'true'";
        }
        leaf-list dual-cpe-sites {
          type leafref {
            path "../../../dual-cpe-site/dual-cpe-site-services/site-name";
            require-instance false;
          }
          description
            "dual-sites";
          when " ../dual-cpe-site = 'true' ";
        }
        leaf single-cpe-dual-wan-site {
          type boolean;
          description
            "single-cpe-dual-wan-site: True/False";
          when "../apply-to-sites = 'true'";
        }
        leaf-list single-cpe-dual-wan-sites {
          type leafref {
            path "../../../single-cpe-dual-wan-site/single-cpe-dual-wan-site-services/site-name";
            require-instance false;
          }
          description
            "single-sites";
          when " ../single-cpe-dual-wan-site = 'true' ";
        }
        leaf dual-cpe-dual-wan-site {
          type boolean;
          description
            "dual-cpe-dual-wan-site: True/False";
          when "../apply-to-sites = 'true'";
        }
        leaf-list dual-cpe-dual-wan-sites {
          type leafref {
            path "../../../dual-cpe-dual-wan-site/dual-cpe-dual-wan-site-services/site-name";
            require-instance false;
          }
          description
            "dual-sites";
          when " ../dual-cpe-dual-wan-site = 'true' ";
        }
        leaf triple-cpe-site {
          type boolean;
          description
            "triple-cpe-site: True/False";
          when "../apply-to-sites = 'true'";
        }
        leaf-list triple-cpe-sites {
          type leafref {
            path "../../../triple-cpe-site/triple-cpe-site-services/site-name";
            require-instance false;
          }
          description
            "single-sites";
          when " ../triple-cpe-site = 'true' ";
        }
      }
    }
  }

  grouping prefix-list-def {
    leaf prefix-list-name {
      type string-no-space;
      description
        "string";
      n-ext:maps-to "/ac:devices/ac:device/l3features:ip-prefixlist-list/ip-prefixlist/name";
    }
    list prefix {
      key "rule-num";
      leaf prefix-name {
        type string-no-space;
        description
          "string";
        n-ext:maps-to "/ac:devices/ac:device/l3features:ip-prefixlist-list/ip-prefixlist[name=current()/../../prefix-list-name]/ip-prefixlist-entries/ip-prefixlist-entry[rule-num=current()/../rule-num]/prefix-name";
      }
      leaf rule-num {
        type uint32 {
          range "1..4294967294";
        }
        description
          "1..4294967294";
        n-ext:maps-to "/ac:devices/ac:device/l3features:ip-prefixlist-list/ip-prefixlist[name=current()/../../prefix-list-name]/ip-prefixlist-entries/ip-prefixlist-entry/rule-num";
      }
      leaf ipv4-prefix {
        //type inet:ipv4-prefix;
        type string-no-space;
        description
          "Valid IPv4 Prefix (A.B.C.D/Z for e.x: 172.16.1.0/24)";
        n-ext:maps-to "/ac:devices/ac:device/l3features:ip-prefixlist-list/ip-prefixlist[name=current()/../../prefix-list-name]/ip-prefixlist-entries/ip-prefixlist-entry[rule-num=current()/../rule-num]/subnet";
      }
      leaf condition {
        type enumeration {
          enum "permit";
          enum "deny";
        }
        description
          "permit
           deny
          ";
        n-ext:maps-to "/ac:devices/ac:device/l3:ip-prefixlist-list/ip-prefixlist[name=current()/../../prefix-list-name]/ip-prefixlist-entries/ip-prefixlist-entry[rule-num=current()/../rule-num]/condition";
      }
      leaf exact-matching-prefix-length {
        type matching-prefix-type;
        description
          "string";
        //n-ext:maps-to "/ac:devices/ac:device/l3:ip-prefixlist-list/ip-prefixlist[name=current()/../../prefix-list-name]/ip-prefixlist-entries/ip-prefixlist-entry[rule-num=current()/../rule-num][compare='eq']/num";
      }
      leaf minimum-matching-prefix-length {
        type matching-prefix-type;
        description
          "string";
        //n-ext:maps-to "/ac:devices/ac:device/l3:ip-prefixlist-list/ip-prefixlist[name=current()/../../prefix-list-name]/ip-prefixlist-entries/ip-prefixlist-entry[rule-num=current()/../rule-num][compare='ge']/num";
      }
      leaf maximum-matching-prefix-length {
        type matching-prefix-type;
        description
          "string";
        //n-ext:maps-to "/ac:devices/ac:device/l3:ip-prefixlist-list/ip-prefixlist[name=current()/../../prefix-list-name]/ip-prefixlist-entries/ip-prefixlist-entry[rule-num=current()/../rule-num][compare='le']/num";
      }
    }
  }

  grouping advertise-network-def {
    leaf name {
      type string-no-space;
      description
        "BGP Advertisement Prefix Name
         This is an internal field for Anuta NCX
        ";
    }
    leaf vrf-name {
      description
        "name";
      type leafref {
        //path "../../../../../../vrfs/vrf/vrf-name";
        path "/ac:services/cpedeployment:managed-cpe-services/customer[name=current()/../../../../../../name]/vrfs/vrf/vrf-name";
      }
      n-ext:maps-to "/ac:devices/ac:device[ac:id=current()/../../../device-ip]/l3:vrfs/vrf/name";
    }
    leaf prefix {
      type inet:ipv4-prefix;
      description
        "Valid IPv4 Prefix (A.B.C.D/Z for e.x: 172.16.1.0/24)";
      mandatory true;
      //n-ext:maps-to "/ac:devices/device[id=current()/../../../device-ip]/l3:vrfs/vrf[name=current()/../vrf-name]/router-bgp/network/ip-address";
      //n-ext:maps-to "/ac:devices/device[id=current()/../../../device-ip]/l3:vrfs/vrf[name=current()/../vrf-name]/router-bgp/network/netmask";
      n-ext:maps-to "/ac:devices/ac:device[ac:id=current()/../../../device-ip]/l3:vrfs/vrf[name=current()/../vrf-name]/router-bgp/network";
      n-ext:prefix-maps-to "ip-address,netmask";
    }
    leaf route-map {
      type leafref {
        //path "../../../../../../route-maps/route-map/route-map-name";
        path "/ac:services/cpedeployment:managed-cpe-services/customer[name=current()/../../../../../../name]/route-maps/route-map/route-map-name";
      }
      n-ext:maps-to "/ac:devices/ac:device[ac:id=current()/../../../device-ip]/l3:vrfs/vrf[name=current()/../vrf-name]/router-bgp/network/route-map";
      description
        "route-map";
    }
    leaf sequence-number {
      type string;
      default "20";
      description
        "sequence-number";
      config false;
    }
  }

  grouping community-list-def {
    leaf extcommunity {
      type boolean;
      description
        "extcommunity: True/False";
    }
    leaf community-list-entry {
      type community-list-entry-type;
      description
        "standard
         expanded
        ";
      default "standard";
      n-ext:maps-to "/ac:devices/ac:device/l3features:community-lists/community-list/community-list-entry";
      n-ext:maps-to "/ac:devices/ac:device/l3features:extcommunity-lists/extcommunity-list/extcommunity-list-entry";
    }
    leaf community-list-name {
      type string-no-space;
      description
        "string";
      n-ext:maps-to "/ac:devices/ac:device/l3features:community-lists/community-list[community-list-entry=current()/../community-list-entry]/community-list-name";
      n-ext:maps-to "/ac:devices/ac:device/l3features:extcommunity-lists/extcommunity-list[extcommunity-list-entry=current()/../extcommunity-list-entry]/extcommunity-list-name";
    }
    leaf condition {
      type condition-type;
      description
        "permit
         deny
        ";
      n-ext:maps-to "/ac:devices/ac:device/l3features:community-lists/community-list[community-list-entry=current()/../community-list-entry]/condition";
      n-ext:maps-to "/ac:devices/ac:device/l3features:extcommunity-lists/extcommunity-list[extcommunity-list-entry=current()/../extcommunity-list-entry]/condition";
    }
    leaf value {
      type string-no-lead-trail-space;
      description
        "string";
      n-ext:maps-to "/ac:devices/ac:device/l3features:community-lists/community-list[community-list-entry=current()/../community-list-entry]/value";
      n-ext:maps-to "/ac:devices/ac:device/l3features:extcommunity-lists/extcommunity-list[extcommunity-list-entry=current()/../extcommunity-list-entry]/value";
    }
    leaf extcomm {
      type enumeration {
        enum "rt";
        enum "soo";
        enum "vpn-distinguisher";
      }
      description
        "rt
         soo
         vpn-distinguisher
        ";
      when " ../community-list-entry = 'standard' and ../extcommunity = 'true'";
      n-ext:maps-to "/ac:devices/ac:device/l3features:extcommunity-lists/extcommunity-list[extcommunity-list-entry=current()/../extcommunity-list-entry]/extcomm";
    }
  }

  grouping extcommunity-list-def {
    leaf extcommunity-list-entry {
      type community-list-entry-type;
      description
        "standard
         expanded
        ";
      default "standard";
    }
    leaf extcommunity-list-name {
      type string-no-space;
      description
        "string";
    }
    leaf condition {
      type condition-type;
      description
        "permit
         deny
        ";
    }
    leaf extcomm {
      type enumeration {
        enum "rt";
        enum "soo";
        enum "vpn-distinguisher";
      }
      description
        "rt
         soo
         vpn-distinguisher
        ";
      when " ../extcommunity-list-entry = 'standard' ";
    }
    leaf value {
      type string-no-lead-trail-space;
      description
        "string";
    }
  }

  grouping sla-responder-def {
    leaf option-name {
      type string;
      default "responder";
      description
        "option-name";
    }
    leaf enable-responder {
      type boolean;
      n-ext:maps-to "/ac:devices/ac:device[ac:id=current()/../../../device-ip]/l3features:ip-sla/responder/is-responder";
      description
        "Check to enable IP SLA Responder";
    }
    leaf sla-logging-traps {
      type boolean;
      n-ext:maps-to "/ac:devices/ac:device[ac:id=current()/../../../device-ip]/l3features:ip-sla/responder/is-logging-traps";
      description
        "Check to enable IP SLA Logging Traps";
    }
    leaf server-twamp {
      type boolean;
      n-ext:maps-to "/ac:devices/ac:device[ac:id=current()/../../../device-ip]/l3features:ip-sla/responder/is-server-twamp";
      description
        "Check to enable IP SLA Server TWAMP";
    }
    leaf server-twamp-port {
      type uint16 {
        range "0..65535";
      }
      n-ext:maps-to "/ac:devices/ac:device[ac:id=current()/../../../device-ip]/l3features:ip-sla/responder/port";
      description
        "Specify IP SLA Server TWAMP Port";
      when "../server-twamp = 'true'";
    }
    leaf responder-twamp {
      type boolean;
      description
        "Enable IP SLA Responder TWAMP";
    }
  }

  grouping sla-def {
    leaf entry-number {
      type uint32 {
        range "1..2147483647";
      }
      n-ext:maps-to "/ac:devices/ac:device[ac:id=current()/../../../device-ip]/l3features:ip-sla/sla/entry-number";
      description
        "Enter number with in the range: 1..2147483647";
    }
    leaf vrf-name {
      description
        "name";
      type leafref {
        //path "../../../../../../vrfs/vrf/vrf-name";
        path "/ac:services/cpedeployment:managed-cpe-services/customer[name=current()/../../../../../../name]/vrfs/vrf/vrf-name";
      }
      //n-ext:maps-to "/ac:devices/device[id=current()/../../../device-ip]/l3:vrfs/vrf/name";
      n-ext:maps-to "/ac:devices/ac:device[ac:id=current()/../../../device-ip]/l3features:ip-sla/sla[entry-number=current()/../entry-number]/vrf-name";
    }
    leaf operation-type {
      type enumeration {
        enum "dhcp";
        enum "dns";
        enum "ethernet";
        enum "exit";
        enum "ftp";
        enum "http";
        enum "icmp-echo";
        enum "icmp-jitter";
        enum "mpls";
        enum "path-echo";
        enum "path-jitter";
        enum "tcp-connect";
        enum "udp-echo";
        enum "udp-jitter";
        enum "voip";
      }
      description
        "Select one of the operttion-type from list:
         dhcp
         dns
         ethernet
         exit
         ftp
         http
         icmp-echo
         icmp-jitter
         mpls
         path-echo
         path-jitter
         tcp-connect
         udp-echo
         udp-jitter
         voip
        ";
      n-ext:maps-to "/ac:devices/ac:device[ac:id=current()/../../../device-ip]/l3features:ip-sla/sla[entry-number=current()/../entry-number]/operation-type";
      mandatory true;
    }
    leaf http-request-type {
      type enumeration {
        enum "raw";
        enum "get";
      }
      description
        "raw
         get
        ";
      when " ../operation-type = 'http' ";
      n-ext:maps-to "/ac:devices/ac:device[ac:id=current()/../../../device-ip]/l3features:ip-sla/sla[entry-number=current()/../entry-number]/http-request-type";
    }
    leaf http-url {
      type string-no-lead-trail-space;
      description
        "string";
      when " ../operation-type = 'http' ";
      n-ext:maps-to "/ac:devices/ac:device[ac:id=current()/../../../device-ip]/l3features:ip-sla/sla[entry-number=current()/../entry-number]/http-url";
    }
    leaf http-raw-request {
      type string;
      description
        "string";
      when " ../operation-type = 'http' ";
      n-ext:maps-to "/ac:devices/ac:device[ac:id=current()/../../../device-ip]/l3features:ip-sla/sla[entry-number=current()/../entry-number]/http-raw-request";
    }
    leaf destination {
      type string-no-lead-trail-space;
      description
        "Hostname or A.B.C.D Destination IP address or hostname";
      //mandatory true;
      n-ext:maps-to "/ac:devices/ac:device[ac:id=current()/../../../device-ip]/l3features:ip-sla/sla[entry-number=current()/../entry-number]/destination";
    }
    leaf source {
      type enumeration {
        enum "source-interface";
        enum "source-ip";
      }
      description
        "source-interface
         source-ip
        ";
      n-ext:maps-to "/ac:devices/ac:device[ac:id=current()/../../../device-ip]/l3features:ip-sla/sla[entry-number=current()/../entry-number]/source";
      mandatory true;
    }
    leaf source-interface-name {
      type string-no-lead-trail-space;
      description
        "string";
      when "../source = 'source-interface' ";
      n-ext:maps-to "/ac:devices/ac:device[ac:id=current()/../../../device-ip]/l3features:ip-sla/sla[entry-number=current()/../entry-number]/source-interface-name";
    }
    leaf source-interface-ip {
      type string-no-lead-trail-space;
      description
        "Valid IPv4/v6 Address (A.B.C.D for e.x: 172.16.1.1 or X::Y for e.x: 2001::1)";
      n-ext:maps-to "/ac:devices/ac:device[ac:id=current()/../../../device-ip]/l3features:ip-sla/sla[entry-number=current()/../entry-number]/source-interface-ip";
      when "../source = 'source-ip' ";
    }
    leaf data-size {
      type uint32 {
        range "0..16384";
      }
      n-ext:maps-to "/ac:devices/ac:device[ac:id=current()/../../../device-ip]/l3features:ip-sla/sla[entry-number=current()/../entry-number]/data-size";
      description
        "<0-16384>  Data Size in bytes ";
    }
    leaf frequency {
      type uint32 {
        range "1..604800";
      }
      n-ext:maps-to "/ac:devices/ac:device[ac:id=current()/../../../device-ip]/l3features:ip-sla/sla[entry-number=current()/../entry-number]/frequency";
      description
        "<1-604800> Frequency in seconds";
    }
    leaf timeout {
      type uint32 {
        range "0..604800000";
      }
      n-ext:maps-to "/ac:devices/ac:device[ac:id=current()/../../../device-ip]/l3features:ip-sla/sla[entry-number=current()/../entry-number]/timeout";
      description
        "<0-604800000> Timeout in milliseconds";
    }
    leaf threshold {
      type uint32;
      n-ext:maps-to "/ac:devices/ac:device[ac:id=current()/../../../device-ip]/l3features:ip-sla/sla[entry-number=current()/../entry-number]/threshold";
      description
        "<0-60000> Threshold in milliseconds";
    }
    leaf track-number {
      type uint16 {
        range "0..1000";
      }
      description
        "Enter number with in the range: 0..1000";
      n-ext:maps-to "/ac:devices/ac:device[ac:id=current()/../../../device-ip]/l3features:tracks/track[entry-number=current()/../entry-number]/track-number";
    }
    leaf sequence-number {
      type string;
      default "22";
      description
        "sequence-number";
      config false;
    }
    leaf response-data-size {
      type uint32 {
        range "20..17512";
      }
      description
        "<20-17512>  Data Size in bytes ";
      when "../operation-type = 'udp-jitter' ";
      n-ext:maps-to "/ac:devices/ac:device[ac:id=current()/../../../device-ip]/l3features:ip-sla/sla[entry-number=current()/../entry-number]/response-data-size";
    }
    leaf destination-port {
      type uint16 {
        range "1..65535";
      }
      description
        "1..65535";
      n-ext:maps-to "/ac:devices/ac:device[ac:id=current()/../../../device-ip]/l3features:ip-sla/sla[entry-number=current()/../entry-number]/destination-port";
    }
    leaf source-port {
      type uint16 {
        range "1..65535";
      }
      description
        "1..65535";
      n-ext:maps-to "/ac:devices/ac:device[ac:id=current()/../../../device-ip]/l3features:ip-sla/sla[entry-number=current()/../entry-number]/source-port";
    }
    leaf interval {
      type uint16 {
        range "4..60000";
      }
      description
        "4..60000";
      n-ext:maps-to "/ac:devices/ac:device[ac:id=current()/../../../device-ip]/l3features:ip-sla/sla[entry-number=current()/../entry-number]/interval";
    }
    leaf tos {
      type uint8 {
        range "0..255";
      }
      description
        "0..255";
      n-ext:maps-to "/ac:devices/ac:device[ac:id=current()/../../../device-ip]/l3features:ip-sla/sla[entry-number=current()/../entry-number]/tos";
    }
    leaf tag {
      type string-no-lead-trail-space;
      description
        "string";
      n-ext:maps-to "/ac:devices/ac:device[ac:id=current()/../../../device-ip]/l3features:ip-sla/sla[entry-number=current()/../entry-number]/tag";
    }
    leaf history-interval {
      type uint16 {
        range "1..3600";
      }
      description
        "1..3600";
      n-ext:maps-to "/ac:devices/ac:device[ac:id=current()/../../../device-ip]/l3features:ip-sla/sla[entry-number=current()/../entry-number]/history-interval";
    }
    leaf buckets-size {
      type uint8 {
        range "1..100";
      }
      description
        "1..100";
      n-ext:maps-to "/ac:devices/ac:device[ac:id=current()/../../../device-ip]/l3features:ip-sla/sla[entry-number=current()/../entry-number]/buckets-size";
    }
    leaf num-packets {
      type uint16 {
        range "1..60000";
      }
      description
        "1..60000";
      n-ext:maps-to "/ac:devices/ac:device[ac:id=current()/../../../device-ip]/l3features:ip-sla/sla[entry-number=current()/../entry-number]/num-packets";
    }
    leaf track-delay-down-time {
      type uint16 {
        range "1..180";
      }
      description
        "1..180";
      // n-ext:maps-to "/ac:devices/device[id=current()/../../../device-ip]/l3features:tracks/track/delay-down-time";
      n-ext:maps-to "/ac:devices/ac:device[ac:id=current()/../../../device-ip]/l3features:tracks/track[entry-number=current()/../entry-number]/delay-down-time";
    }
    leaf track-delay-up-time {
      type uint16 {
        range "1..180";
      }
      description
        "1..180";
      // n-ext:maps-to "/ac:devices/device[id=current()/../../../device-ip]/l3features:tracks/track/delay-up-time";
      n-ext:maps-to "/ac:devices/ac:device[ac:id=current()/../../../device-ip]/l3features:tracks/track[entry-number=current()/../entry-number]/delay-up-time";
    }
  }

  grouping list-def {
    leaf list-track-number {
      type uint16 {
        range "0..1000";
      }
      description
        "Enter number with in the range: 0..1000";
      n-ext:maps-to "/ac:devices/ac:device[ac:id=current()/../../../device-ip]/l3features:tracks/track/track-number";
    }
    leaf list-type {
      type enumeration {
        enum "boolean";
        enum "threshold";
      }
      default "boolean";
      description
        "Track List Type";
      n-ext:maps-to "/ac:devices/ac:device[ac:id=current()/../../../device-ip]/l3features:tracks/track[track-number=current()/../list-track-number]/list-type";
    }
    leaf boolean-type {
      type enumeration {
        enum "or";
        enum "and";
      }
      default "or";
      description
        "Track List Boolean Type";
      n-ext:maps-to "/ac:devices/ac:device[ac:id=current()/../../../device-ip]/l3features:tracks/track[track-number=current()/../list-track-number]/boolean-type";
    }
    leaf zscaler-mgmt {
      type boolean;
      description
        "Check to activate Zscaler Track and EEM management templates";
    }
    list object-list {
      key "object-number";
      leaf object-number {
        //type string-no-space;
        type uint16 {
          range "0..1000";
        }
        description
          "Track List Object Number";
        n-ext:maps-to "/ac:devices/ac:device[ac:id=current()/../../../../device-ip]/l3features:tracks/track[track-number=current()/../../list-track-number]/object-list/object-number";
      }
      leaf not {
        type boolean;
        description
          "Deletes a previously configured track based on whether an interface object is not up or down";
        n-ext:maps-to "/ac:devices/ac:device[ac:id=current()/../../../../device-ip]/l3features:tracks/track[track-number=current()/../../list-track-number]/object-list[object-number=current()/../object-number]/not";
      }
    }
  }

  grouping bgp-adv-props {
    description
      "BGP advertisement properties";
    leaf redistribute-connected {
      type boolean;
      description
        "redistribute-connected: True/False";
      default "true";
      config false;
    }
    leaf redistribute-connected-route-policy {
      type leafref {
        //path "../../../../route-maps/route-map/route-map-name";
        path "/ac:services/cpedeployment:managed-cpe-services/customer[name=current()/../../../../name]/route-maps/route-map/route-map-name";
      }
      description
        "redistribute-connected-route-policy";
      when " ../redistribute-connected = 'true' ";
      config false;
    }
    leaf interface-name {
      type leafref {
        //path "/ac:devices/ac:device[ac:id=current()/../device-ip]/if:interfaces/if:interface/if:name";
        path "/ac:devices/ac:device/if:interfaces/if:interface/if:name";
      }
      description
        "interface-name";
      //n-ext:maps-to "/ac:devices/ac:device/if:interfaces/interface/name";
      when " ../redistribute-connected = 'true' ";
      config false;
    }
    leaf redistribute-static {
      type boolean;
      description
        "redistribute-static: True/False";
      config false;
    }
    leaf redistribute-static-route-policy {
      type leafref {
        //path "../../../../route-maps/route-map/route-map-name";
        path "/ac:services/cpedeployment:managed-cpe-services/customer[name=current()/../../../../name]/route-maps/route-map/route-map-name";
      }
      description
        "redistribute-static-route-policy";
      when " ../redistribute-static = 'true' ";
      config false;
    }
    leaf aggregate-summary-networks {
      type boolean;
      description
        "aggregate-summary-networks: True/False";
      config false;
    }
    leaf summary-networks {
      type string;
      description
        "string";
      when " ../aggregate-summary-networks = 'true' ";
      //n-ext:maps-to "/ac:devices/ac:device/l3:vrfs/vrf/router-bgp/aggregate-summary-network/network";
      config false;
    }
  }

  grouping bgp-def {
    leaf bgp-community-new {
      type boolean;
      description
        "bgp-community-new: True/False";
      n-ext:maps-to "/ac:devices/device[ac:id=current()/../../../device-ip]/basicDeviceConfigs:bgp/bgp-community-new";
      when " ../bgp-settings = 'true' ";
    }
    leaf peer-groups {
      type boolean;
      description
        "peer-groups: True/False";
      when "../bgp-settings = 'true' ";
    }
    // Change 22/05/2018: Make peer-group a leaf-list and move listen-cidr at peer-group customer level
    leaf-list peer-group {
      /*type leafref {
        //path "../../../../../../bgp-peer-groups/bgp-peer-group/peer-group";
        path "/ac:services/cpedeployment:managed-cpe-services/customer[name=current()/../../../../../../name]/bgp-peer-groups/bgp-peer-group/peer-group";
      }*/
      type peer-group;
      description
        "string";
      n-ext:maps-to "/ac:devices/ac:device[ac:id=current()/../../../device-ip]/l3:vrfs/vrf[name=current()/../vrf-name]/router-bgp/peer-group/name";
      n-ext:maps-to "/ac:devices/ac:device[ac:id=current()/../../../device-ip]/l3:vrfs/vrf[name=GLOBAL]/router-bgp/listen-range/name";
      when " ../bgp-settings = 'true' and ../peer-groups = 'true'";
    }
    leaf listen-cidr {
      type inet:ipv4-prefix;
      description
        "Valid IPv4 Prefix (A.B.C.D/Z for e.x: 172.16.1.0/24)";
      config false;
      n-ext:maps-to "/ac:devices/ac:device[ac:id=current()/../../../device-ip]/l3:vrfs/vrf[name=current()/../vrf-name]/router-bgp/listen-range/cidr";
      when " ../bgp-settings = 'true' ";
    }
  }

  grouping vrouter-local-def {
    description
      "Routing specific properties which are applicable for this service";
    leaf bgp-router-id {
      type inet:ip-address;
      description
        "BGP Router-ID";
      config false;
      n-ext:maps-to "/ac:devices/ac:device[ac:id=current()/../device-ip]/l3:vrfs/vrf/router-bgp/router-id";
    }
    container vrfs {
      leaf sequence-number {
        type string;
        default "2";
        description
          "sequence-number";
        config false;
      }
      uses vrf-list-def;
    }
    container nat {
      leaf sequence-number {
        type string;
        default "8";
        description
          "sequence-number";
        config false;
      }
      uses nat-list-def;
    }
    container route-maps {
      leaf sequence-number {
        type string;
        default "13";
        description
          "sequence-number";
        config false;
      }
      uses route-maps-def-list;
    }
    container community-lists {
      leaf sequence-number {
        type string;
        default "15";
        description
          "sequence-number";
        config false;
      }
      uses community-lists-ref-def;
    }
    //container extcommunity-lists {
    //  leaf sequence-number {
    //    type string;
    //    default "4";
    //    description
    //      "sequence-number";
    //    config false;
    //  }
    //  uses extcommunity-lists-ref-def;
    //}
    container prefix-lists {
      leaf sequence-number {
        type string;
        default "17";
        description
          "sequence-number";
        config false;
      }
      uses prefix-lists-def-list;
    }
    container advertise-networks {
      leaf sequence-number {
        type string;
        default "19";
        description
          "sequence-number";
        config false;
      }
      list advertise-network {
        key "name";
        uses advertise-network-def;
      }
    }
    container ip-sla {
      leaf sequence-number {
        type string;
        default "21";
        description
          "sequence-number";
        config false;
      }
      list sla {
        key "entry-number";
        uses sla-def;
      }
      list list-entry {
        key "list-track-number";
        uses list-def;
      }
      list responder-options {
        key "option-name";
        uses sla-responder-def;
      }
    }
    container access-lists {
      leaf sequence-number {
        type string;
        default "23";
        description
          "sequence-number";
        config false;
      }
      list access-list {
        key "name";
        uses feature-acl-def;
      }
    }
    container class-maps {
      leaf sequence-number {
        type string;
        default "26";
        description
          "sequence-number";
        config false;
      }
      uses class-maps-def-list;
    }
    container ospfs {
      leaf sequence-number {
        type string;
        default "28";
        description
          "sequence-number";
        config false;
      }
      list router-ospf {
        key "process-id";
        uses ospf-def;
      }
    }
    container eigrp {
      leaf sequence-number {
        type string;
        default "32";
        description
          "sequence-number";
        config false;
      }
      list router-eigrp {
        key "process-id";
        uses eigrp-def;
      }
    }
    container loopback {
      leaf sequence-number {
        type string;
        default "5";
        description
          "sequence-number";
        config false;
      }
      list loopback {
        key "loopback-interface-id";
        uses loopback-def;
      }
    }
    container crypto-isakmp-peers {
      list peers {
        key "peer-address";
        uses crypto-isakmp-peer-def;
      }
    }
    container acl-template {
      list acl {
        key "acl-name";
        leaf acl-name {
          type leafref {
            path "/ac:services/cpedeployment:managed-cpe-services/customer[name=current()/../../../../../../name]/access-lists/access-list/name";
          }
          description
            "acl-name";
          n-ext:maps-to "/ac:devices/ac:device[ac:id=current()/../../../device-ip]/acl:access-lists/acl:access-list/acl:name";
        }
      }
    }
    container bridge {
      uses bridge-def;
    }
    container mac-acl {
      uses mac-acl-def;
    }
    uses bgp-adv-props;
  }

  grouping eigrp-def {
    leaf sequence-number {
      type string;
      default "33";
      description
        "sequence-number";
      config false;
    }
    leaf process-id {
      type uint16 {
        range "1..65535";
      }
      n-ext:maps-to "/ac:devices/ac:device[ac:id=current()/../../../device-ip]/l3:vrfs/vrf[name=current()/../vrf-name]/router-eigrp/eigrp/process-id";
      description
        "1..65535";
    }
    leaf vrf-name {
      description
        "name";
      type leafref {
        //path "../../../../../../vrfs/vrf/vrf-name";
        path "/ac:services/cpedeployment:managed-cpe-services/customer[name=current()/../../../../../../name]/vrfs/vrf/vrf-name";
      }
      n-ext:maps-to "/ac:devices/ac:device[ac:id=current()/../../../device-ip]/l3:vrfs/vrf/name";
    }
    leaf router-id {
      type inet:ip-address;
      description
        "string";
      n-ext:maps-to "/ac:devices/ac:device[ac:id=current()/../../../device-ip]/l3:vrfs/vrf[name=current()/../vrf-name]/router-eigrp/eigrp[process-id=current()/../process-id]/router-id";
    }
    leaf nsf {
      type boolean;
      description
        "nsf: True/False";
      n-ext:maps-to "/ac:devices/ac:device[ac:id=current()/../../../device-ip]/l3:vrfs/vrf[name=current()/../vrf-name]/router-eigrp/eigrp[process-id=current()/../process-id]/nsf";
    }
    leaf eigrp-stub {
      type enumeration {
        enum "receive-only";
        enum "connected";
        enum "static";
        enum "summary";
      }
      description
        "receive-only
         connected
         static
         summary
        ";
      n-ext:maps-to "/ac:devices/ac:device[ac:id=current()/../../../device-ip]/l3:vrfs/vrf[name=current()/../vrf-name]/router-eigrp/eigrp[process-id=current()/../process-id]/eigrp-stub";
    }
    leaf ip-address {
      type inet:ipv4-address;
      description
        "Valid IPv4 Address (A.B.C.D for e.x: 172.16.1.1)";
      config false;
    }
    leaf wildcard {
      type string-no-space;
      description
        "string";
      config false;
    }
    leaf distance-internal-routes {
      type uint8;
      description
        "Enter EIGRP Distance for internal routes";
      n-ext:maps-to "/ac:devices/ac:device[ac:id=current()/../../../device-ip]/l3:vrfs/vrf[name=current()/../vrf-name]/router-eigrp/eigrp[process-id=current()/../process-id]/internal-route-distance";
    }
    leaf distance-external-routes {
      type uint8;
      description
        "Enter EIGRP Distance for external routes";
      n-ext:maps-to "/ac:devices/ac:device[ac:id=current()/../../../device-ip]/l3:vrfs/vrf[name=current()/../vrf-name]/router-eigrp/eigrp[process-id=current()/../process-id]/external-route-distance";
    }
    leaf default-metric {
      type boolean;
      description
        "Check to Configure EIGRP Default Metric values";
    }
    leaf bandwidth-metric {
      type uint32 {
        range "1..4294967295";
      }
      description
        "Enter Bandwidth Metric Value";
      n-ext:maps-to "/ac:devices/ac:device[ac:id=current()/../../../device-ip]/l3:vrfs/vrf[name=current()/../vrf-name]/router-eigrp/eigrp[process-id=current()/../process-id]/default-metric/bandwidth-metric";
      when "../default-metric = 'true'";
    }
    leaf delay-metric {
      type uint32 {
        range "0..4294967295";
      }
      description
        "Enter Delay Metric Value";
      n-ext:maps-to "/ac:devices/ac:device[ac:id=current()/../../../device-ip]/l3:vrfs/vrf[name=current()/../vrf-name]/router-eigrp/eigrp[process-id=current()/../process-id]/default-metric/delay-metric";
      when "../default-metric = 'true'";
    }
    leaf reliability-metric {
      type uint8 {
        range "0..255";
      }
      description
        "Enter Reliability Metric Value";
      n-ext:maps-to "/ac:devices/ac:device[ac:id=current()/../../../device-ip]/l3:vrfs/vrf[name=current()/../vrf-name]/router-eigrp/eigrp[process-id=current()/../process-id]/default-metric/reliability-metric";
      when "../default-metric = 'true'";
    }
    leaf load-metric {
      type uint8 {
        range "0..255";
      }
      description
        "Enter Load Metric Value";
      n-ext:maps-to "/ac:devices/ac:device[ac:id=current()/../../../device-ip]/l3:vrfs/vrf[name=current()/../vrf-name]/router-eigrp/eigrp[process-id=current()/../process-id]/default-metric/load-metric";
      when "../default-metric = 'true'";
    }
    leaf mtu-metric {
      type uint16 {
        range "1..65535";
      }
      description
        "Enter MTU Metric Value";
      n-ext:maps-to "/ac:devices/ac:device[ac:id=current()/../../../device-ip]/l3:vrfs/vrf[name=current()/../vrf-name]/router-eigrp/eigrp[process-id=current()/../process-id]/default-metric/mtu";
      when "../default-metric = 'true'";
    }
    list passive-interface {
      key "interface";
      leaf sequence-number {
        type string;
        default "34";
        description
          "sequence-number";
        config false;
      }
      leaf interface {
        type union {
          type leafref {
            path "/ac:devices/ac:device[ac:id=current()/../../../../device-ip]/if:interfaces/if:interface/if:name";
            require-instance false;
          }
          type string-no-lead-trail-space;
        }
        n-ext:maps-to "/ac:devices/ac:device[ac:id=current()/../../../../device-ip]/l3:vrfs/vrf[name=current()/../../vrf-name]/router-eigrp/eigrp[process-id=current()/../../process-id]/passive-interface/interface";
        default "default";
        description
          "Select or Enter Passive Interface Name";
      }
      leaf passive-interface {
        type boolean;
        description
          "Check if interface should be configured as passive";
        default "true";
        n-ext:maps-to "/ac:devices/ac:device[ac:id=current()/../../../../device-ip]/l3:vrfs/vrf[name=current()/../../vrf-name]/router-eigrp/eigrp[process-id=current()/../../process-id]/passive-interface/passive-interface";
      }
    }
    list network {
      key "prefix";
      leaf sequence-number {
        type string;
        default "35";
        description
          "sequence-number";
        config false;
      }
      leaf prefix {
        type inet:ipv4-prefix;
        description
          "Enter Network IPv4 Prefix (Eg: 10.0.0.0/24)";
        n-ext:maps-to "/ac:devices/ac:device[ac:id=current()/../../../../device-ip]/l3:vrfs/vrf[name=current()/../../vrf-name]/router-eigrp/eigrp[process-id=current()/../../process-id]/network";
        //n-ext:maps-to "/ac:devices/device[id=current()/../../../../device-ip]/l3:vrfs/vrf[name=current()/../../vrf-name]/router-eigrp/eigrp[process-id=current()/../../process-id]/network/ip-address";
        //n-ext:maps-to "/ac:devices/device[id=current()/../../../../device-ip]/l3:vrfs/vrf[name=current()/../../vrf-name]/router-eigrp/eigrp[process-id=current()/../../process-id]/network/wild-card";
        n-ext:prefix-maps-to "ip-address,,wild-card";
      }
    }
    container redistribute {
      leaf sequence-number {
        type string;
        default "36";
        description
          "sequence-number";
        config false;
      }
      leaf redistribute-eigrp-on-bgp {
        type boolean;
        description
          "Check to redistribute EIGRP process into Site BGP process";
      }
      leaf route-map {
        type leafref {
          //path "../../../../../../../route-maps/route-map/route-map-name";
          path "/ac:services/cpedeployment:managed-cpe-services/customer[name=current()/../../../../../../../name]/route-maps/route-map/route-map-name";
        }
        n-ext:maps-to "/ac:devices/ac:device[ac:id=current()/../../../../device-ip]/l3features:vrfs/vrf[name=current()/../../vrf-name]/router-bgp/redistribute[protocol=eigrp]/route-map";
        description
          "Select Redistribute Route-Map";
        when "../redistribute-eigrp-on-bgp = 'true'";
      }
      list redistribute-on-eigrp {
        key "protocol";
        uses eigrp-redistribute;
      }
    }
  }

  grouping eigrp-redistribute {
    leaf sequence-number {
      type string;
      default "37";
      description
        "sequence-number";
      config false;
    }
    leaf protocol {
      type eigrp-protocol;
      description
        "Select Protocol To Redistribute in EIGRP";
      n-ext:maps-to "/ac:devices/ac:device[ac:id=current()/../../../../../device-ip]/l3:vrfs/vrf[name=current()/../../../vrf-name]/router-eigrp/eigrp[process-id=current()/../../../process-id]/redistribute/protocol";
    }
    leaf as-number {
      type uint16 {
        range "1..65535";
      }
      description
        "Enter EIGRP AS Number To redistribute in EIGRP";
      when " ../protocol = 'eigrp' ";
      n-ext:maps-to "/ac:devices/ac:device[ac:id=current()/../../../../../device-ip]/l3:vrfs/vrf[name=current()/../../../vrf-name]/router-eigrp/eigrp[process-id=current()/../../../process-id]/redistribute[protocol=eigrp]/as-number";
    }
    leaf ospf-id {
      type uint16 {
        range "1..65535";
      }
      description
        "Enter OSPF Process ID To redistribute Site in EIGRP";
      when " ../protocol = 'ospf' ";
      n-ext:maps-to "/ac:devices/ac:device[ac:id=current()/../../../../../device-ip]/l3:vrfs/vrf[name=current()/../../../vrf-name]/router-eigrp/eigrp[process-id=current()/../../../process-id]/redistribute[protocol=ospf]/ospf-id";
    }
    leaf route-map {
      type leafref {
        path "/ac:services/cpedeployment:managed-cpe-services/customer[name=current()/../../../../../../../../name]/route-maps/route-map/route-map-name";
      }
      description
        "Select Redistribution Route-Map";
      n-ext:maps-to "/ac:devices/ac:device[ac:id=current()/../../../../../device-ip]/l3:vrfs/vrf[name=current()/../../../vrf-name]/router-eigrp/eigrp[process-id=current()/../../../process-id]/redistribute[protocol=current()/../protocol]/route-map";
    }
    leaf bandwidth-metric {
      type uint64 {
        range "1..4294967295";
      }
      description
        "Enter EIGRP Redistribution Bandwidth Metric";
      n-ext:maps-to "/ac:devices/ac:device[ac:id=current()/../../../../../device-ip]/l3:vrfs/vrf[name=current()/../../../vrf-name]/router-eigrp/eigrp[process-id=current()/../../../process-id]/redistribute[protocol=current()/../protocol]/bandwidth-metric";
    }
    leaf delay-metric {
      type uint64 {
        range "0..4294967295";
      }
      description
        "Enter EIGRP Redistribution Delay Metric";
      n-ext:maps-to "/ac:devices/ac:device[ac:id=current()/../../../../../device-ip]/l3:vrfs/vrf[name=current()/../../../vrf-name]/router-eigrp/eigrp[process-id=current()/../../../process-id]/redistribute[protocol=current()/../protocol]/delay-metric";
    }
    leaf reliability-metric {
      type uint16 {
        range "0..255";
      }
      description
        "Enter EIGRP Redistribution Reliability Metric";
      n-ext:maps-to "/ac:devices/ac:device[ac:id=current()/../../../../../device-ip]/l3:vrfs/vrf[name=current()/../../../vrf-name]/router-eigrp/eigrp[process-id=current()/../../../process-id]/redistribute[protocol=current()/../protocol]/reliability-metric";
    }
    leaf load-metric {
      type uint16 {
        range "1..255";
      }
      description
        "Enter EIGRP Redistribution Load Metric";
      n-ext:maps-to "/ac:devices/ac:device[ac:id=current()/../../../../../device-ip]/l3:vrfs/vrf[name=current()/../../../vrf-name]/router-eigrp/eigrp[process-id=current()/../../../process-id]/redistribute[protocol=current()/../protocol]/load-metric";
    }
    leaf mtu {
      type uint16 {
        range "1..65535";
      }
      description
        "Enter EIGRP Redistribution MTU Metric";
      n-ext:maps-to "/ac:devices/ac:device[ac:id=current()/../../../../../device-ip]/l3:vrfs/vrf[name=current()/../../../vrf-name]/router-eigrp/eigrp[process-id=current()/../../../process-id]/redistribute[protocol=current()/../protocol]/mtu";
    }
    list interface {
      //key "interface-name sequence-number";
      key "route-map-connected-sequence-number";
      leaf sequence-number {
        type uint8 {
          range "105..120";
        }
        default "105";
        description
          "sequence-number: This is NCX internal reference. By default 105 is the value, in case if any key issues value can be changed";
      }
      leaf route-map-connected-sequence-number {
        type leafref {
          path "/ac:services/cpedeployment:managed-cpe-services/customer[name=current()/../../../../../../../../../name]/route-maps/route-map[route-map-name=current()/../../route-map]/route-map-entries/sequence-number";
        }
        n-ext:maps-to "/ac:devices/ac:device[ac:id=current()/../../../../../../device-ip]/l3:route-maps/route-map[name=current()/../../route-map]/route-map-entries/seq";
        description
          "Enter Redistribute Connected Route-Map Sequence Number
           This should match the sequence number that has the LAN-INTERFACE keyword
          ";
      }
      leaf interface-name {
        type union {
          type leafref {
            path "/ac:devices/ac:device[ac:id=current()/../../../../../../device-ip]/if:interfaces/if:interface/if:name";
            require-instance false;
          }
          type string-no-lead-trail-space;
        }
        //n-ext:maps-to "/ac:devices/device[id=current()/../../../../device-ip]/if:interfaces/if:interface[vrf=current()/../../vrf-name]/if:name";
        //n-ext:maps-to "/ac:devices/device[id=current()/../../../../device-ip]/if:interfaces/if:interface[l3:vrf=current()/../../vrf-name]/if:name";
        //n-ext:maps-to "/ac:devices/device[id=current()/../../../../device-ip]/if:interfaces/if:interface/if:name";
        n-ext:maps-to "/ac:devices/device[ac:id=current()/../../../../../../device-ip]/l3:route-maps/route-map[name=current()/../../route-map]/route-map-entries[seq=current()/../route-map-connected-sequence-number]/match-condition[condition-type=interface]/value";
        description
          "Enter Interface Name(s) to be part of the Redistribute Connected Route-Map
           This will replace the LAN-INTERFACE keyword with the interface(s) specified";
      }
    }
  }

  grouping nat-list-def {
    list pool {
      key "pool-name";
      leaf sequence-number {
        type string;
        default "9";
        description
          "sequence-number";
        config false;
      }
      uses pool-def;
    }
    list address-translation {
      key "list value";
      leaf sequence-number {
        type string;
        default "10";
        description
          "sequence-number";
        config false;
      }
      uses address-translation-def;
    }
    list static {
      key "static inside-ip inside-global-ip";
      leaf sequence-number {
        type string;
        default "11";
        description
          "sequence-number";
        config false;
      }
      uses static-def;
    }
    list translation {
      key "nat-flow";
      leaf sequence-number {
        type string;
        default "12";
        description
          "sequence-number";
        config false;
      }
      uses translation-def;
    }
  }

  grouping static-def {
    leaf side {
      type enumeration {
        enum "inside";
        enum "outside";
      }
      description
        "Select Static NAT entry direction (inside/outside)";
      n-ext:maps-to "/ac:devices/ac:device[ac:id=current()/../../../device-ip]/l3features:ip-nat/address-translation[nat-list=static]/side";
    }
    leaf address-translation {
      type enumeration {
        enum "source";
      }
      description
        "Select NAT Translation Source/Destination";
      n-ext:maps-to "/ac:devices/ac:device[ac:id=current()/../../../device-ip]/l3features:ip-nat/address-translation[nat-list=static]/address-translation";
    }
    leaf static {
      type enumeration {
        enum "static";
      }
      description
        "Select NAT Static Entry";
      n-ext:maps-to "/ac:devices/ac:device[ac:id=current()/../../../device-ip]/l3features:ip-nat/address-translation[nat-list=static]/nat-list";
    }
    leaf network {
      type boolean;
      description
        "Check if static NAT entry is based on IPv4 Prefix";
    }
    leaf inside-ip {
      //type string;
      type inet:ipv4-address;
      description
        "Enter static NAT entry inside local IP";
      n-ext:maps-to "/ac:devices/ac:device[ac:id=current()/../../../device-ip]/l3features:ip-nat/address-translation[nat-list=static]/value";
    }
    leaf inside-global-ip {
      //type string;
      type inet:ipv4-address;
      description
        "Enter static NAT entry inside global IP";
      n-ext:maps-to "/ac:devices/ac:device[ac:id=current()/../../../device-ip]/l3features:ip-nat/address-translation[nat-list=static]/inside-global-ip";
    }
    leaf route-map {
      type leafref {
        path "/ac:services/cpedeployment:managed-cpe-services/customer[name=current()/../../../../../../name]/route-maps/route-map/route-map-name";
      }
      description
        "Select Route-Map to be applied to static NAT entry";
      n-ext:maps-to "/ac:devices/ac:device[ac:id=current()/../../../device-ip]/l3features:ip-nat/address-translation[nat-list=static]/route-map-name";
      when " ../network = 'false' ";
    }
    leaf prefix-length {
      //type string;
      type uint8 {
        range "0..32";
      }
      description
        "Enter static NAT entry network prefix length";
      when " ../network = 'true' ";
      n-ext:maps-to "/ac:devices/ac:device[ac:id=current()/../../../device-ip]/l3features:ip-nat/address-translation[nat-list=static]/prefix-length";
    }
  }

  grouping translation-def {
    leaf nat-flow {
      type enumeration {
        enum "dns-timeout";
        enum "finrst-timeout";
        enum "icmp-timeout";
        enum "port-timeout";
        enum "pptp-timeout";
        enum "routemap-entry-timeout";
        enum "syn-timeout";
        enum "tcp-timeout";
        enum "timeout";
        enum "udp-timeout";
      }
      description
        "dns-timeout
         finrst-timeout
         icmp-timeout
         port-timeout
         pptp-timeout
         routemap-entry-timeout
         syn-timeout
         tcp-timeout
         timeout
         udp-timeout
        ";
      n-ext:maps-to "/ac:devices/ac:device[ac:id=current()/../../../device-ip]/l3features:ip-nat/nat-translation/nat-flow";
    }
    leaf timeout {
      type union {
        type enumeration {
          enum "never";
        }
        type uint16;
      }
      description
        "Union Input types:
         enumeration
         uint16
        ";
      n-ext:maps-to "/ac:devices/ac:device[ac:id=current()/../../../device-ip]/l3features:ip-nat/nat-translation/timeout";
    }
  }

  grouping pool-def {
    leaf pool-name {
      type string-no-space;
      description
        "string";
      n-ext:maps-to "/ac:devices/ac:device[ac:id=current()/../../../device-ip]/l3features:ip-nat-pool/pool/pool-name";
    }
    leaf start-ip {
      type inet:ip-address;
      description
        "Enter NAT Pool Start IP Address";
      n-ext:maps-to "/ac:devices/ac:device[ac:id=current()/../../../device-ip]/l3features:ip-nat-pool/pool[pool-name=current()/../pool-name]/start-ip";
    }
    leaf end-ip {
      type inet:ip-address;
      description
        "Enter NAT Pool End IP Address";
      n-ext:maps-to "/ac:devices/ac:device[ac:id=current()/../../../device-ip]/l3features:ip-nat-pool/pool[pool-name=current()/../pool-name]/end-ip";
    }
    leaf mask {
      type enumeration {
        enum "netmask";
        enum "prefix-length";
      }
      n-ext:maps-to "/ac:devices/ac:device[ac:id=current()/../../../device-ip]/l3features:ip-nat-pool/pool[pool-name=current()/../pool-name]/mask";
      description
        "Select NAT Pool Mask Type";
    }
    leaf netmask {
      type inet:ip-address;
      description
        "Enter NAT Pool Subnet Mask";
      n-ext:maps-to "/ac:devices/ac:device[ac:id=current()/../../../device-ip]/l3features:ip-nat-pool/pool[pool-name=current()/../pool-name]/netmask";
      when " ../mask = 'netmask' ";
    }
    leaf prefix-length {
      type uint8;
      description
        "Enter NAT Pool Prefix Length";
      when " ../mask = 'prefix-length' ";
      n-ext:maps-to "/ac:devices/ac:device[ac:id=current()/../../../device-ip]/l3features:ip-nat-pool/pool[pool-name=current()/../pool-name]/prefix-length";
    }
    leaf pool-type {
      type enumeration {
        enum "match-host";
        enum "rotary";
      }
      description
        "Select NAT Pool Type";
      n-ext:maps-to "/ac:devices/ac:device[ac:id=current()/../../../device-ip]/l3features:ip-nat-pool/pool[pool-name=current()/../pool-name]/pool-type";
    }
  }

  grouping address-translation-def {
    leaf side {
      type enumeration {
        enum "inside";
        enum "outside";
      }
      description
        "Select NAT entry direction (inside/outside)";
      n-ext:maps-to "/ac:devices/ac:device[ac:id=current()/../../../device-ip]/l3features:ip-nat/address-translation/side";
    }
    leaf address-translation {
      type enumeration {
        enum "source";
      }
      description
        "Select NAT entry Source";
      n-ext:maps-to "/ac:devices/ac:device[ac:id=current()/../../../device-ip]/l3features:ip-nat/address-translation/address-translation";
    }
    leaf list {
      type enumeration {
        enum "list";
      }
      description
        "Select NAT entry ACL type";
      n-ext:maps-to "/ac:devices/ac:device[ac:id=current()/../../../device-ip]/l3features:ip-nat/address-translation/nat-list";
    }
    leaf value {
      type string-no-lead-trail-space;
      description
        "Enter ACL Name
         NOTE: This ACL needs to be manually created within the Site service under cpe container
        ";
      n-ext:maps-to "/ac:devices/ac:device[ac:id=current()/../../../device-ip]/l3features:ip-nat/address-translation/value";
    }
    list pool {
      key "pool-name";
      leaf sequence-number {
        type string;
        default "7";
        description
          "sequence-number";
        config false;
      }
      leaf pool-name {
        type string-no-lead-trail-space;
        description
          "Enter NAT Pool Name";
        n-ext:maps-to "/ac:devices/ac:device[ac:id=current()/../../../../device-ip]/l3features:ip-nat/address-translation/pool/pool-name";
      }
      leaf vrf {
        type string-no-lead-trail-space;
        description
          "Enter NAT Pool VRF Name";
        n-ext:maps-to "/ac:devices/ac:device[ac:id=current()/../../../../device-ip]/l3features:ip-nat/address-translation/pool[pool-name=current()/../pool-name]/vrf";
      }
      leaf overload {
        type boolean;
        description
          "Check if NAT overload";
        n-ext:maps-to "/ac:devices/ac:device[ac:id=current()/../../../../device-ip]/l3features:ip-nat/address-translation/pool[pool-name=current()/../pool-name]/overload";
      }
    }
    list interface {
      key "interface-name";
      leaf sequence-number {
        type string;
        default "8";
        description
          "sequence-number";
        config false;
      }
      leaf interface-name {
        type string-no-lead-trail-space;
        description
          "Enter NAT Outside Interface Name";
        n-ext:maps-to "/ac:devices/ac:device[ac:id=current()/../../../../device-ip]/l3features:ip-nat/address-translation/interface/interface-name";
      }
      leaf vrf {
        type string-no-lead-trail-space;
        description
          "Enter NAT Outside Interface VRF";
        n-ext:maps-to "/ac:devices/ac:device[ac:id=current()/../../../../device-ip]/l3features:ip-nat/address-translation/interface[interface-name=current()/../interface-name]/vrf";
      }
      leaf overload {
        type boolean;
        description
          "Check if NAT Outside Interface Overload";
        n-ext:maps-to "/ac:devices/ac:device[ac:id=current()/../../../../device-ip]/l3features:ip-nat/address-translation/interface[interface-name=current()/../interface-name]/overload";
      }
    }
  }

  grouping loopback-def {
    leaf sequence-number {
      type string;
      default "6";
      description
        "sequence-number";
      config false;
    }
    leaf loopback-interface-id {
      type uint8;
      description
        "Enter Loopback Interface ID";
      //n-ext:maps-to "/ac:devices/device[id=current()/../../../device-ip]/if:interfaces/interface[long-name=Loopback]/long-name";
    }
    leaf cidr {
      type leafref {
        path "/ip:ipaddress-pools/ip:ipaddress-pool/ip:name";
      }
      n-ext-ui:ncx-ext-pagination "paginate";
      description
        "Enter Loopback Interface CIDR";
      //n-ext:maps-to "/ac:devices/device[id=current()/../../../device-ip]/if:interfaces/interface[long-name=current()/../interface-name]";
      //n-ext:prefix-maps-to "ip-address,netmask";
    }
    leaf interface-name {
      type string-no-lead-trail-space;
      description
        "Enter Loopback Interface Full Name
         NOTE: This field is only required for Brownfield service
        ";
      n-ext:maps-to "/ac:devices/ac:device[ac:id=current()/../../../device-ip]/if:interfaces/interface[if-type=softwareLoopback]/long-name";
    }
    leaf ip {
      type inet:ipv4-address;
      description
        "Enter Loopback interface IP Address";
      n-ext:maps-to "/ac:devices/ac:device[ac:id=current()/../../../device-ip]/if:interfaces/interface[long-name=current()/../interface-name]/ip-address";
    }
    leaf vrf {
      type leafref {
        //path "../../../../../../vrfs/vrf/vrf-name";
        path "/ac:services/cpedeployment:managed-cpe-services/customer[name=current()/../../../../../../name]/vrfs/vrf/vrf-name";
      }
      //n-ext:maps-to "/ac:devices/device[id=current()/../../../device-ip]/l3:vrfs/vrf/name";
      n-ext:maps-to "/ac:devices/ac:device[ac:id=current()/../../../device-ip]/if:interfaces/interface[long-name=current()/../interface-name]/vrf";
      description
        "Select Loopback Interface VRF";
      //mandatory true;
    }
    leaf description {
      type string;
      n-ext:maps-to "/ac:devices/ac:device[ac:id=current()/../../../device-ip]/if:interfaces/interface[long-name=current()/../interface-name]/description";
      description
        "Enter Loopback Interface Description";
    }
  }

  grouping ospf-def {
    leaf sequence-number {
      type string;
      default "29";
      description
        "sequence-number";
      config false;
    }
    leaf process-id {
      type uint16 {
        range "1..65535";
      }
      n-ext:maps-to "/ac:devices/ac:device[ac:id=current()/../../../device-ip]/l3:vrfs/vrf[name=current()/../vrf-name]/router-ospf/process-id";
      description
        "1..65535";
    }
    leaf vrf-name {
      description
        "name";
      type leafref {
        //path "../../../../../../vrfs/vrf/vrf-name";
        path "/ac:services/cpedeployment:managed-cpe-services/customer[name=current()/../../../../../../name]/vrfs/vrf/vrf-name";
      }
      n-ext:maps-to "/ac:devices/ac:device[ac:id=current()/../../../device-ip]/l3:vrfs/vrf/name";
    }
    leaf router-id {
      type inet:ip-address;
      description
        "OSPF Router-ID";
      n-ext:maps-to "/ac:devices/ac:device[ac:id=current()/../../../device-ip]/l3:vrfs/vrf[name=current()/../vrf-name]/router-ospf[process-id=current()/../process-id]/router-id";
    }
    leaf reference-bandwidth {
      type uint32 {
        range "1..4294967";
      }
      n-ext:maps-to "/ac:devices/ac:device[ac:id=current()/../../../device-ip]/l3:vrfs/vrf[name=current()/../vrf-name]/router-ospf[process-id=current()/../process-id]/reference-bandwidth";
      description
        "OSPF Reference Bandwidth";
      default "1000";
    }
    leaf snmp {
      type boolean;
      description
        "snmp: True/False";
    }
    leaf context {
      type string;
      description
        "string";
      when "../snmp = 'true'";
      n-ext:maps-to "/ac:devices/ac:device[ac:id=current()/../../../device-ip]/l3:vrfs/vrf[name=current()/../vrf-name]/router-ospf[process-id=current()/../process-id]/context";
    }
    leaf community {
      type string;
      description
        "string";
      when "../snmp = 'true'";
      n-ext:maps-to "/ac:devices/ac:device[ac:id=current()/../../../device-ip]/l3:vrfs/vrf[name=current()/../vrf-name]/router-ospf[process-id=current()/../process-id]/community";
    }
    leaf access {
      type access-id;
      description
        "ro
         rw
        ";
      when "../snmp = 'true'";
      n-ext:maps-to "/ac:devices/ac:device[ac:id=current()/../../../device-ip]/l3:vrfs/vrf[name=current()/../vrf-name]/router-ospf[process-id=current()/../process-id]/access";
    }
    leaf global-acl-name {
      type leafref {
        path "/ac:services/cpedeployment:managed-cpe-services/customer[name=current()/../../../../../../name]/access-lists/access-list/name";
      }
      n-ext:maps-to "/ac:devices/ac:device[ac:id=current()/../../../device-ip]/l3:vrfs/vrf[name=current()/../vrf-name]/router-ospf[process-id=current()/../process-id]/acl-name";
      description
        "global-acl-name";
      when "../snmp = 'true'";
    }
    leaf site-acl-name {
      type string-no-space;
      description
        "string";
      when "../snmp = 'true'";
      n-ext:maps-to "/ac:devices/ac:device[ac:id=current()/../../../device-ip]/l3:vrfs/vrf[name=current()/../vrf-name]/router-ospf[process-id=current()/../process-id]/acl-name";
    }
    leaf maximum-paths {
      type uint16 {
        range "1..32";
      }
      n-ext:maps-to "/ac:devices/ac:device[ac:id=current()/../../../device-ip]/l3:vrfs/vrf[name=current()/../vrf-name]/router-ospf[process-id=current()/../process-id]/maximum-paths";
      description
        "1..32";
      //default "1";
    }
    leaf default-information {
      type boolean;
      description
        "Check to advertise OSPF Default Route";
      //n-ext:maps-to "/ac:devices/ac:device[ac:id=current()/../../../device-ip]/l3:vrfs/vrf[name=current()/../vrf-name]/router-ospf[process-id=current()/../process-id]/default-information";
    }
    leaf default-inf-key1 {
      type default-inf-key;
      description
        "metric
         metric-type
         route-map
        ";
      when "../default-information = 'true'";
      config false;
    }
    leaf default-inf-key2 {
      type default-inf-key;
      description
        "metric
         metric-type
         route-map
        ";
      when "../default-information = 'true'";
      config false;
    }
    leaf default-inf-key3 {
      type default-inf-key;
      description
        "metric
         metric-type
         route-map
        ";
      when "../default-information = 'true'";
      config false;
    }
    leaf default-inf-always {
      type boolean;
      description
        "Check to always advertise Default Route from OSPF";
      when "../default-information = 'true'";
    }
    leaf default-inf-metric {
      type uint32 {
        range "0..16777214";
      }
      //n-ext:maps-to "/ac:devices/device[id=current()/../../../device-ip]/l3:vrfs/vrf[name=current()/../vrf-name]/router-ospf[process-id=current()/../process-id]/default-inf-metric";
      n-ext:maps-to "/ac:devices/ac:device[ac:id=current()/../../../device-ip]/l3:vrfs/vrf[name=current()/../vrf-name]/router-ospf[process-id=current()/../process-id]/inject-default-route/metric";
      description
        "Enter OSPF Default Route Metric";
      //default "500";
      when "../default-information = 'true'";
    }
    leaf default-inf-metric-type {
      type uint8 {
        range "1..2";
      }
      description
        "Enter OSPF Default Route Metric-Type";
      //default "1";
      when "../default-information = 'true'";
      n-ext:maps-to "/ac:devices/ac:device[ac:id=current()/../../../device-ip]/l3:vrfs/vrf[name=current()/../vrf-name]/router-ospf[process-id=current()/../process-id]/inject-default-route/metric-type";
    }
    leaf default-inf-route-map {
      type leafref {
        //path "../../../../../../route-maps/route-map/route-map-name";
        path "/ac:services/cpedeployment:managed-cpe-services/customer[name=current()/../../../../../../name]/route-maps/route-map/route-map-name";
      }
      description
        "Enter OSPF Default Route Metric-Type";
      when "../default-information = 'true'";
      n-ext:maps-to "/ac:devices/ac:device[ac:id=current()/../../../device-ip]/l3:vrfs/vrf[name=current()/../vrf-name]/router-ospf[process-id=current()/../process-id]/inject-default-route/route-map";
    }
    leaf distribute-list {
      type boolean;
      description
        "distribute-list: True/False";
    }
    leaf dis-list-route-map {
      type leafref {
        //path "../../../../../../route-maps/route-map/route-map-name";
        path "/ac:services/cpedeployment:managed-cpe-services/customer[name=current()/../../../../../../name]/route-maps/route-map/route-map-name";
      }
      n-ext:maps-to "/ac:devices/ac:device[ac:id=current()/../../../device-ip]/l3:vrfs/vrf[name=current()/../vrf-name]/router-ospf[process-id=current()/../process-id]/dis-list-route-map";
      description
        "dis-list-route-map";
      when "../distribute-list = 'true'";
    }
    leaf dis-list-route-update {
      type route-update;
      description
        "in
         out
        ";
      when "../distribute-list = 'true'";
      n-ext:maps-to "/ac:devices/ac:device[ac:id=current()/../../../device-ip]/l3:vrfs/vrf[name=current()/../vrf-name]/router-ospf[process-id=current()/../process-id]/dis-list-route-update";
    }
    container redistribute {
      list redistribute-on-ospf {
        key "protocol";
        uses ospf-redistribute;
      }
      leaf sequence-number {
        type string;
        default "30";
        description
          "sequence-number";
        config false;
      }
      leaf redistribute-ospf-on-bgp {
        type boolean;
        description
          "Check to Redistribute OSPF process into Site BGP Process";
      }
      leaf ospf-internal {
        type boolean;
        description
          "Check to Redistribute OSPF Internal Routes";
        when "../redistribute-ospf-on-bgp = 'true'";
        n-ext:maps-to "/ac:devices/ac:device[ac:id=current()/../../../../device-ip]/l3features:vrfs/vrf[name=current()/../../vrf-name]/router-bgp/redistribute[protocol=ospf]/ospf-internal";
      }
      leaf ospf-external1 {
        type boolean;
        description
          "Check to Redistribute OSPF External E1 Routes";
        when "../redistribute-ospf-on-bgp = 'true'";
      }
      leaf ospf-external2 {
        type boolean;
        description
          "Check to Redistribute OSPF External E2 Routes";
        when "../redistribute-ospf-on-bgp = 'true'";
      }
      leaf route-map {
        type leafref {
          //path "../../../../../../../route-maps/route-map/route-map-name";
          path "/ac:services/cpedeployment:managed-cpe-services/customer[name=current()/../../../../../../../name]/route-maps/route-map/route-map-name";
        }
        //n-ext:maps-to "/ac:devices/device[id=current()/../../../../device-ip]/l3:vrfs/vrf[name=current()/../vrf-name]/router-ospf[process-id=current()/../process-id]/redistribute/ospf-redistribute/route-map";
        n-ext:maps-to "/ac:devices/ac:device[ac:id=current()/../../../../device-ip]/l3features:vrfs/vrf[name=current()/../../vrf-name]/router-bgp/redistribute[protocol=ospf]/route-map";
        description
          "Select Redistribution Route-Map";
        when "../redistribute-ospf-on-bgp = 'true'";
      }
    }
  }

  grouping custom-nbar-def {
    leaf name {
      type string-no-space;
      description
        "Enter NBAR Custom Signature App Name";
    }
    leaf id {
      type uint16;
      description
        "Enter NBAR Custom Signature Unique ID";
      config false;
    }
    leaf direction {
      type enumeration {
        enum "any";
        enum "source";
        enum "destination";
      }
      description
        "Select Traffic Direction to match";
    }
    leaf custom-nbar-type {
      type enumeration {
        enum "transport";
        enum "http";
        enum "ssl";
      }
      description
        "Select NBAR Custom Signature Type";
    }
    leaf http-url {
      type string-no-space;
      description
        "Enter HTTP URL";
      when "../custom-nbar-type = 'http'";
    }
    leaf ssl-sni {
      type string-no-space;
      description
        "SSL Server Name Indication (SNI) or Common Name (CN)";
      when "../custom-nbar-type = 'ssl'";
    }
    leaf transport-type {
      type enumeration {
        enum "tcp";
        enum "udp";
        enum "tcp-udp";
      }
      description
        "Select Transport Type";
      when "../custom-nbar-type = 'transport'";
    }
    leaf ip-type {
      type enumeration {
        enum "ip-address";
        enum "subnet";
      }
      description
        "Select the type of IP object to match (individual addresses or subnet)";
      when "../custom-nbar-type = 'transport'";
    }
    leaf-list ip-address {
      type string;
      description
        "Valid IPv4 Address (A.B.C.D for e.x: 172.16.1.1)";
      when "../ip-type = 'ip-address'";
    }
    leaf subnet-address {
      type inet:ipv4-address;
      description
        "Enter Subnet Address (eg: 192.168.1.0, 10.128.0.0)";
      when "../ip-type = 'subnet'";
    }
    leaf subnet-length {
      type uint8;
      description
        "Enter Subnet Length";
      when "../ip-type = 'subnet'";
    }
    leaf port-type {
      type enumeration {
        enum "single-port";
        enum "port-range";
      }
      description
        "Select whether you want to configure individual TCP/UDP ports or range of ports";
      when "../custom-nbar-type = 'transport'";
    }
    leaf-list port-number {
      type string;
      description
        "Enter Port Number";
      when "../port-type = 'single-port'";
    }
    leaf start-port {
      type uint16;
      description
        "Enter TCP/UDP start port number from the range";
      when "../port-type = 'port-range'";
    }
    leaf end-port {
      type uint16;
      description
        "Enter TCP/UDP end port number from the range";
      when "../port-type = 'port-range'";
    }
  }

  grouping ospf-redistribute {
    leaf sequence-number {
      type string;
      default "31";
      description
        "sequence-number";
      config false;
    }
    leaf protocol {
      type ospf-protocol;
      description
        "Enter OSPF Redistribute Protocol";
      mandatory true;
      n-ext:maps-to "/ac:devices/ac:device[ac:id=current()/../../../../../device-ip]/l3:vrfs/vrf[name=current()/../../../vrf-name]/router-ospf[process-id=current()/../../../process-id]/redistribute/ospf-redistribute/protocol";
    }
    leaf process-id {
      type uint16 {
        range "1..65535";
      }
      description
        "Enter OSPF Process ID";
      when "../protocol = 'ospf'";
      n-ext:maps-to "/ac:devices/ac:device[ac:id=current()/../../../../../device-ip]/l3:vrfs/vrf[name=current()/../../../vrf-name]/router-ospf[process-id=current()/../../../process-id]/redistribute/ospf-redistribute[protocol=current()/../protocol]/process-id-entry";
    }
    leaf route-map {
      type leafref {
        //path "../../../../../../../../route-maps/route-map/route-map-name";
        path "/ac:services/cpedeployment:managed-cpe-services/customer[name=current()/../../../../../../../../name]/route-maps/route-map/route-map-name";
      }
      n-ext:maps-to "/ac:devices/ac:device[ac:id=current()/../../../../../device-ip]/l3:vrfs/vrf[name=current()/../../../vrf-name]/router-ospf[process-id=current()/../../../process-id]/redistribute/ospf-redistribute[protocol=current()/../protocol]/route-map";
      description
        "Enter OSPF Redistribution Route-Map";
    }
    leaf key1 {
      type key;
      description
        "string";
      config false;
    }
    leaf key2 {
      type key;
      description
        "string";
      config false;
    }
    leaf metric {
      type uint32 {
        range "0..16777214";
      }
      n-ext:maps-to "/ac:devices/ac:device[ac:id=current()/../../../../../device-ip]/l3:vrfs/vrf[name=current()/../../../vrf-name]/router-ospf[process-id=current()/../../../process-id]/redistribute/ospf-redistribute[protocol=current()/../protocol]/value1";
      description
        "Enter OSPF Redistribute Metric Value";
    }
    leaf metric-type {
      type uint8 {
        range "1..2";
      }
      description
        "Enter OSPF Redistribute Metric Type (1 for E1 / 2 for E2)";
      n-ext:maps-to "/ac:devices/ac:device[ac:id=current()/../../../../../device-ip]/l3:vrfs/vrf[name=current()/../../../vrf-name]/router-ospf[process-id=current()/../../../process-id]/redistribute/ospf-redistribute[protocol=current()/../protocol]/value2";
    }
    leaf tag {
      type uint32 {
        range "0..4294967295";
      }
      n-ext:maps-to "/ac:devices/ac:device[ac:id=current()/../../../../../device-ip]/l3:vrfs/vrf[name=current()/../../../vrf-name]/router-ospf[process-id=current()/../../../process-id]/redistribute/ospf-redistribute[protocol=current()/../protocol]/tag";
      description
        "Enter OSPF Redistribute Tag";
    }
    list interface {
      //key "interface-name sequence-number";
      key "route-map-connected-sequence-number";
      leaf sequence-number {
        type uint8 {
          range "105..120";
        }
        default "106";
        description
          "sequence-number: This is NCX internal reference. By default 106 is the value, in case if any key issues value can be changed";
      }
      leaf route-map-connected-sequence-number {
        type leafref {
          path "/ac:services/cpedeployment:managed-cpe-services/customer[name=current()/../../../../../../../../../name]/route-maps/route-map[route-map-name=current()/../../route-map]/route-map-entries/sequence-number";
        }
        n-ext:maps-to "/ac:devices/ac:device[ac:id=current()/../../../../../../device-ip]/l3:route-maps/route-map[name=current()/../../route-map]/route-map-entries/seq";
        description
          "Enter Redistribute Connected Route-Map Sequence Number
           This should match the sequence number that has the LAN-INTERFACE keyword
          ";
      }
      leaf interface-name {
        type union {
          type leafref {
            path "/ac:devices/ac:device[ac:id=current()/../../../../../../device-ip]/if:interfaces/if:interface/if:name";
            require-instance false;
          }
          type string-no-lead-trail-space;
        }
        //n-ext:maps-to "/ac:devices/device[id=current()/../../../../device-ip]/if:interfaces/if:interface[vrf=current()/../../vrf-name]/if:name";
        //n-ext:maps-to "/ac:devices/device[id=current()/../../../../device-ip]/if:interfaces/if:interface[l3:vrf=current()/../../vrf-name]/if:name";
        //n-ext:maps-to "/ac:devices/device[id=current()/../../../../device-ip]/if:interfaces/if:interface/if:name";
        n-ext:maps-to "/ac:devices/ac:device[ac:id=current()/../../../../../../device-ip]/l3:route-maps/route-map[name=current()/../../route-map]/route-map-entries[seq=current()/../route-map-connected-sequence-number]/match-condition[condition-type=interface]/value";
        description
          "Enter Interface Name(s) to be part of the Redistribute Connected Route-Map
           This will replace the LAN-INTERFACE keyword by the interface(s) specified";
      }
    }
  }

  grouping community-lists-def {
    container community-lists {
      //n-ext:ignore-for-brownfield;
      list community-list {
        key "community-list-name value";
        uses community-list-def;
      }
      list update-community-list {
        n-ext:ignore-for-brownfield;
        key "id";
        leaf id {
          type string-no-space;
          description
            "Enter Transaction ID
             This is an internal field for Anuta NCX
            ";
        }
        leaf community-list-name {
          type leafref {
            path "/ac:services/cpedeployment:managed-cpe-services/customer[name=current()/../../../name]/community-lists/community-list/community-list-name";
          }
          description
            "Select Community List Name";
          mandatory true;
          //n-ext:maps-to "/ac:devices/device/l3features:community-lists/community-list[community-list-entry=current()/../community-list-entry]/community-list-name";
          //n-ext:maps-to "/ac:devices/device/l3features:extcommunity-lists/extcommunity-list[extcommunity-list-entry=current()/../extcommunity-list-entry]/extcommunity-list-name";
        }
        leaf update-profile {
          type boolean;
          description
            "Check to update customer template";
        }
        leaf operation {
          type operation-def;
          description
            "CREATE
             DELETE
            ";
        }
        leaf extcommunity {
          type boolean;
          description
            "Check if this is an extended community";
        }
        leaf community-list-entry {
          type community-list-entry-type;
          description
            "Select the Community List Type\n";
          default "standard";
          when "../operation = 'CREATE'";
          //n-ext:maps-to "/ac:devices/device/l3features:community-lists/community-list[community-list-name=current()/../community-list-name]/community-list-entry";
          //n-ext:maps-to "/ac:devices/device/l3features:extcommunity-lists/extcommunity-list[extcommunity-list-name=current()/../extcommunity-list-name]/extcommunity-list-entry";
        }
        leaf condition {
          type condition-type;
          description
            "Select Community List Condition";
          when "../operation = 'CREATE'";
          //n-ext:maps-to "/ac:devices/device/l3features:community-lists/community-list[community-list-name=current()/../community-list-name]/condition";
          //n-ext:maps-to "/ac:devices/device/l3features:extcommunity-lists/extcommunity-list[extcommunity-list-name=current()/../extcommunity-list-name]/condition";
        }
        leaf value {
          type string-no-lead-trail-space;
          description
            "Enter Community Value(s) to match";
          mandatory true;
          //n-ext:maps-to "/ac:devices/device/l3features:community-lists/community-list[community-list-name=current()/../community-list-name]/value";
          //n-ext:maps-to "/ac:devices/device/l3features:extcommunity-lists/extcommunity-list[extcommunity-list-name=current()/../extcommunity-list-name]/value";
        }
        leaf extcomm {
          type enumeration {
            enum "rt";
            enum "soo";
            enum "vpn-distinguisher";
          }
          description
            "rt
             soo
             vpn-distinguisher
            ";
          when " ../community-list-entry = 'standard' and ../extcommunity = 'true'";
          //n-ext:maps-to "/ac:devices/device/l3features:extcommunity-lists/extcommunity-list[extcommunity-list-name=current()/../extcommunity-list-name]/extcomm";
        }
        leaf apply-to-sites {
          type boolean;
          description
            "Check if you want to perform bulk update operation on individual sites";
          when "../apply-to-device-group = 'false'";
        }
        leaf apply-to-device-group {
          type boolean;
          description
            "Check if you want to perform bulk update operation on device group";
          when "../apply-to-sites = 'false'";
        }
        leaf device-group {
          type leafref {
            path "/ac:data-grouping/ac:definition/ac:name";
          }
          description
            "device-group";
          when "../apply-to-device-group = 'true'";
        }
        leaf single-cpe-site {
          type boolean;
          description
            "single-cpe-site: True/False";
          when "../apply-to-sites = 'true'";
        }
        leaf-list single-cpe-sites {
          type leafref {
            path "../../../single-cpe-site/single-cpe-site-services/site-name";
            require-instance false;
          }
          description
            "single-sites";
          when " ../single-cpe-site = 'true' ";
        }
        leaf dual-cpe-site {
          type boolean;
          description
            "dual-cpe-site: True/False";
          when "../apply-to-sites = 'true'";
        }
        leaf-list dual-cpe-sites {
          type leafref {
            path "../../../dual-cpe-site/dual-cpe-site-services/site-name";
            require-instance false;
          }
          description
            "dual-sites";
          when " ../dual-cpe-site = 'true' ";
        }
        leaf single-cpe-dual-wan-site {
          type boolean;
          description
            "single-cpe-dual-wan-site: True/False";
          when "../apply-to-sites = 'true'";
        }
        leaf-list single-cpe-dual-wan-sites {
          type leafref {
            path "../../../single-cpe-dual-wan-site/single-cpe-dual-wan-site-services/site-name";
            require-instance false;
          }
          description
            "single-sites";
          when " ../single-cpe-dual-wan-site = 'true' ";
        }
        leaf dual-cpe-dual-wan-site {
          type boolean;
          description
            "dual-cpe-dual-wan-site: True/False";
          when "../apply-to-sites = 'true'";
        }
        leaf-list dual-cpe-dual-wan-sites {
          type leafref {
            path "../../../dual-cpe-dual-wan-site/dual-cpe-dual-wan-site-services/site-name";
            require-instance false;
          }
          description
            "dual-sites";
          when " ../dual-cpe-dual-wan-site = 'true' ";
        }
        leaf triple-cpe-site {
          type boolean;
          description
            "triple-cpe-site: True/False";
          when "../apply-to-sites = 'true'";
        }
        leaf-list triple-cpe-sites {
          type leafref {
            path "../../../triple-cpe-site/triple-cpe-site-services/site-name";
            require-instance false;
          }
          description
            "single-sites";
          when " ../triple-cpe-site = 'true' ";
        }
      }
    }
  }

  grouping extcommunity-lists-def {
    container extcommunity-lists {
      list extcommunity-list {
        key "extcommunity-list-name value";
        uses extcommunity-list-def;
      }
    }
  }

  grouping bgp-peer-props {
    description
      "Properties relating to the BGP route selection process";
    leaf BGP-peer-name {
      type string-no-space;
      description
        "BGP Peer Name
         This is an internal field for Anuta NCX
        ";
    }
    leaf peer-ip {
      type inet:ipv4-address;
      description
        "Valid IPv4 Address (A.B.C.D for e.x: 172.16.1.1)";
      mandatory true;
      //when " ../peer = 'peer-ip' ";
      n-ext:maps-to "/ac:devices/ac:device[ac:id=current()/../../device-ip]/l3:vrfs/vrf[name=current()/../../vrf]/router-bgp/neighbor/ip-address";
      n-ext:maps-to "/ac:devices/ac:device[ac:id=current()/../../device-ip]/l3:vrfs/vrf[name=GLOBAL]/router-bgp/neighbor/ip-address";
      n-ext:maps-to "/ac:devices/ac:device[ac:id=current()/../../device-ip]/l3:vrfs/vrf[name=current()/../../ivrf]/router-bgp/neighbor/ip-address";
    }
    leaf peer-description {
      type string;
      description
        "string";
      n-ext:maps-to "/ac:devices/ac:device[ac:id=current()/../../device-ip]/l3:vrfs/vrf[name=current()/../../vrf]/router-bgp/neighbor[ip-address=current()/../peer-ip]/description";
      n-ext:maps-to "/ac:devices/ac:device[ac:id=current()/../../device-ip]/l3:vrfs/vrf[name=GLOBAL]/router-bgp/neighbor[ip-address=current()/../peer-ip]/description";
      n-ext:maps-to "/ac:devices/ac:device[ac:id=current()/../../device-ip]/l3:vrfs/vrf[name=current()/../../ivrf]/router-bgp/neighbor[ip-address=current()/../peer-ip]/description";
    }
    leaf remote-as {
      type inet:as-number;
      //mandatory true;
      description
        "string";
      n-ext:maps-to "/ac:devices/ac:device[ac:id=current()/../../device-ip]/l3:vrfs/vrf[name=current()/../../vrf]/router-bgp/neighbor[ip-address=current()/../peer-ip]/remote-as";
      n-ext:maps-to "/ac:devices/ac:device[ac:id=current()/../../device-ip]/l3:vrfs/vrf[name=GLOBAL]/router-bgp/neighbor[ip-address=current()/../peer-ip]/remote-as";
      n-ext:maps-to "/ac:devices/ac:device[ac:id=current()/../../device-ip]/l3:vrfs/vrf[name=current()/../../ivrf]/router-bgp/neighbor[ip-address=current()/../peer-ip]/remote-as";
      //n-ext:maps-to "/ac:devices/device[id=current()/../../device-ip]/l3:vrfs/vrf/router-bgp/peer-group/remote-as";
    }
    leaf password {
      type string-no-space;
      description
        "string";
      n-ext:maps-to "/ac:devices/ac:device[ac:id=current()/../../device-ip]/l3:vrfs/vrf[name=current()/../../vrf]/router-bgp/neighbor[ip-address=current()/../peer-ip]/password";
      n-ext:maps-to "/ac:devices/ac:device[ac:id=current()/../../device-ip]/l3:vrfs/vrf[name=GLOBAL]/router-bgp/neighbor[ip-address=current()/../peer-ip]/password";
      n-ext:maps-to "/ac:devices/ac:device[ac:id=current()/../../device-ip]/l3:vrfs/vrf[name=current()/../../ivrf]/router-bgp/neighbor[ip-address=current()/../peer-ip]/password";
      //n-ext:maps-to "/ac:devices/device[id=current()/../../device-ip]/l3:vrfs/vrf/router-bgp/peer-group/password";
    }
    leaf import-route-map {
      type leafref {
        //path "../../../../../../route-maps/route-map/route-map-name";
        path "/ac:services/cpedeployment:managed-cpe-services/customer[name=current()/../../../../../../name]/route-maps/route-map/route-map-name";
      }
      description
        "import-route-map";
      n-ext:maps-to "/ac:devices/ac:device[ac:id=current()/../../device-ip]/l3:vrfs/vrf[name=current()/../../vrf]/router-bgp/neighbor[ip-address=current()/../peer-ip]/in-route-map";
      n-ext:maps-to "/ac:devices/ac:device[ac:id=current()/../../device-ip]/l3:vrfs/vrf[name=GLOBAL]/router-bgp/neighbor[ip-address=current()/../peer-ip]/in-route-map";
      n-ext:maps-to "/ac:devices/ac:device[ac:id=current()/../../device-ip]/l3:vrfs/vrf[name=current()/../../ivrf]/router-bgp/neighbor[ip-address=current()/../peer-ip]/in-route-map";
      //n-ext:maps-to "/ac:devices/device[id=current()/../../device-ip]/l3:vrfs/vrf/router-bgp/peer-group/in-route-map";
    }
    leaf export-route-map {
      type leafref {
        //path "../../../../../../route-maps/route-map/route-map-name";
        path "/ac:services/cpedeployment:managed-cpe-services/customer[name=current()/../../../../../../name]/route-maps/route-map/route-map-name";
      }
      description
        "export-route-map";
      n-ext:maps-to "/ac:devices/ac:device[ac:id=current()/../../device-ip]/l3:vrfs/vrf[name=current()/../../vrf]/router-bgp/neighbor[ip-address=current()/../peer-ip]/out-route-map";
      n-ext:maps-to "/ac:devices/ac:device[ac:id=current()/../../device-ip]/l3:vrfs/vrf[name=GLOBAL]/router-bgp/neighbor[ip-address=current()/../peer-ip]/out-route-map";
      n-ext:maps-to "/ac:devices/ac:device[ac:id=current()/../../device-ip]/l3:vrfs/vrf[name=current()/../../ivrf]/router-bgp/neighbor[ip-address=current()/../peer-ip]/out-route-map";
      //n-ext:maps-to "/ac:devices/device[id=current()/../../device-ip]/l3:vrfs/vrf/router-bgp/peer-group/out-route-map";
    }
    leaf peer-group {
      type leafref {
        //path "../../../../../../bgp-peer-groups/bgp-peer-group/peer-group";
        path "/ac:services/cpedeployment:managed-cpe-services/customer[name=current()/../../../../../../name]/bgp-peer-groups/bgp-peer-group/peer-group";
      }
      description
        "peer-group";
      n-ext:maps-to "/ac:devices/ac:device[ac:id=current()/../../device-ip]/l3:vrfs/vrf[name=current()/../../vrf]/router-bgp/neighbor[ip-address=current()/../peer-ip]/peer-group";
      n-ext:maps-to "/ac:devices/ac:device[ac:id=current()/../../device-ip]/l3:vrfs/vrf[name=GLOBAL]/router-bgp/neighbor[ip-address=current()/../peer-ip]/peer-group";
      n-ext:maps-to "/ac:devices/ac:device[ac:id=current()/../../device-ip]/l3:vrfs/vrf[name=current()/../../ivrf]/router-bgp/neighbor[ip-address=current()/../peer-ip]/peer-group";
    }
    leaf next-hop-self {
      type boolean;
      description
        "next-hop-self: True/False";
      n-ext:maps-to "/ac:devices/ac:device[ac:id=current()/../../device-ip]/l3:vrfs/vrf[name=current()/../../vrf]/router-bgp/neighbor[ip-address=current()/../peer-ip]/next-hop-self";
      n-ext:maps-to "/ac:devices/ac:device[ac:id=current()/../../device-ip]/l3:vrfs/vrf[name=GLOBAL]/router-bgp/neighbor[ip-address=current()/../peer-ip]/next-hop-self";
      n-ext:maps-to "/ac:devices/ac:device[ac:id=current()/../../device-ip]/l3:vrfs/vrf[name=current()/../../ivrf]/router-bgp/neighbor[ip-address=current()/../peer-ip]/next-hop-self";
      //n-ext:maps-to "/ac:devices/device[id=current()/../../device-ip]/l3:vrfs/vrf/router-bgp/peer-group/next-hop-self";
    }
    leaf soft-reconfiguration {
      type boolean;
      description
        "soft-reconfiguration: True/False";
      n-ext:maps-to "/ac:devices/ac:device[ac:id=current()/../../device-ip]/l3:vrfs/vrf[name=current()/../../vrf]/router-bgp/neighbor[ip-address=current()/../peer-ip]/soft-reconfiguration";
      n-ext:maps-to "/ac:devices/ac:device[ac:id=current()/../../device-ip]/l3:vrfs/vrf[name=GLOBAL]/router-bgp/neighbor[ip-address=current()/../peer-ip]/soft-reconfiguration";
      n-ext:maps-to "/ac:devices/ac:device[ac:id=current()/../../device-ip]/l3:vrfs/vrf[name=current()/../../ivrf]/router-bgp/neighbor[ip-address=current()/../peer-ip]/soft-reconfiguration";
      //n-ext:maps-to "/ac:devices/device[id=current()/../../device-ip]/l3:vrfs/vrf/router-bgp/peer-group/soft-reconfiguration";
    }
    leaf default-originate {
      type boolean;
      description
        "default-originate: True/False";
      n-ext:maps-to "/ac:devices/ac:device[ac:id=current()/../../device-ip]/l3:vrfs/vrf[name=current()/../../vrf]/router-bgp/neighbor[ip-address=current()/../peer-ip]/default-originate";
      n-ext:maps-to "/ac:devices/ac:device[ac:id=current()/../../device-ip]/l3:vrfs/vrf[name=GLOBAL]/router-bgp/neighbor[ip-address=current()/../peer-ip]/default-originate";
      n-ext:maps-to "/ac:devices/ac:device[ac:id=current()/../../device-ip]/l3:vrfs/vrf[name=current()/../../ivrf]/router-bgp/neighbor[ip-address=current()/../peer-ip]/default-originate";
      //n-ext:maps-to "/ac:devices/device[id=current()/../../device-ip]/l3:vrfs/vrf/router-bgp/peer-group/default-originate";
    }
    leaf ebgp-multihop {
      type uint8;
      description
        "Enter eBGP Multi-Hop Value";
      n-ext:maps-to "/ac:devices/ac:device[ac:id=current()/../../device-ip]/l3:vrfs/vrf[name=current()/../../vrf]/router-bgp/neighbor[ip-address=current()/../peer-ip]/ebgp-multihop";
      n-ext:maps-to "/ac:devices/ac:device[ac:id=current()/../../device-ip]/l3:vrfs/vrf[name=GLOBAL]/router-bgp/neighbor[ip-address=current()/../peer-ip]/ebgp-multihop";
      n-ext:maps-to "/ac:devices/ac:device[ac:id=current()/../../device-ip]/l3:vrfs/vrf[name=current()/../../ivrf]/router-bgp/neighbor[ip-address=current()/../peer-ip]/ebgp-multihop";
    }
    leaf update-source {
      type string-no-lead-trail-space;
      description
        "Enter eBGP Peering Source Interface";
      n-ext:maps-to "/ac:devices/ac:device[ac:id=current()/../../device-ip]/l3:vrfs/vrf[name=current()/../../vrf]/router-bgp/neighbor[ip-address=current()/../peer-ip]/local-interface";
      n-ext:maps-to "/ac:devices/ac:device[ac:id=current()/../../device-ip]/l3:vrfs/vrf[name=GLOBAL]/router-bgp/neighbor[ip-address=current()/../peer-ip]/local-interface";
      n-ext:maps-to "/ac:devices/ac:device[ac:id=current()/../../device-ip]/l3:vrfs/vrf[name=current()/../../ivrf]/router-bgp/neighbor[ip-address=current()/../peer-ip]/local-interface";
    }
    leaf default-originate-route-map {
      type leafref {
        //path "../../../../../../route-maps/route-map/route-map-name";
        path "/ac:services/cpedeployment:managed-cpe-services/customer[name=current()/../../../../../../name]/route-maps/route-map/route-map-name";
      }
      description
        "default-originate-route-map";
      when "../default-originate = 'true'";
      n-ext:maps-to "/ac:devices/ac:device[ac:id=current()/../../device-ip]/l3:vrfs/vrf[name=current()/../../vrf]/router-bgp/neighbor[ip-address=current()/../peer-ip]/def-originate-route-map";
      n-ext:maps-to "/ac:devices/ac:device[ac:id=current()/../../device-ip]/l3:vrfs/vrf[name=GLOBAL]/router-bgp/neighbor[ip-address=current()/../peer-ip]/def-originate-route-map";
      n-ext:maps-to "/ac:devices/ac:device[ac:id=current()/../../device-ip]/l3:vrfs/vrf[name=current()/../../ivrf]/router-bgp/neighbor[ip-address=current()/../peer-ip]/def-originate-route-map";
      //     n-ext:maps-to "/ac:devices/device/l3:vrfs/vrf/router-bgp/peer-group/def-originate-route-map";
    }
    leaf send-community {
      type boolean;
      description
        "send-community: True/False";
      n-ext:maps-to "/ac:devices/ac:device[ac:id=current()/../../device-ip]/l3:vrfs/vrf[name=current()/../../vrf]/router-bgp/neighbor[ip-address=current()/../peer-ip]/send-community";
      n-ext:maps-to "/ac:devices/ac:device[ac:id=current()/../../device-ip]/l3:vrfs/vrf[name=GLOBAL]/router-bgp/neighbor[ip-address=current()/../peer-ip]/send-community";
      n-ext:maps-to "/ac:devices/ac:device[ac:id=current()/../../device-ip]/l3:vrfs/vrf[name=current()/../../ivrf]/router-bgp/neighbor[ip-address=current()/../peer-ip]/send-community";
      //n-ext:maps-to "/ac:devices/device[id=current()/../../device-ip]/l3:vrfs/vrf/router-bgp/peer-group/send-community";
    }
    leaf encrypted-password {
      type boolean;
      description
        "encrypted-password: True/False";
      n-ext:maps-to "/ac:devices/ac:device[ac:id=current()/../../device-ip]/l3:vrfs/vrf[name=current()/../../vrf]/router-bgp/neighbor[ip-address=current()/../peer-ip]/encryption";
      config false;
    }
    leaf advertisement-interval {
      type boolean;
      description
        "advertisement-interval: True/False";
      //n-ext:maps-to "/ac:devices/device[id=current()/../../device-ip]/l3:vrfs/vrf[name=current()/../../vrf]/router-bgp/neighbor[ip-address=current()/../peer-ip]/advertisement-interval";
      //n-ext:maps-to "/ac:devices/device[id=current()/../../device-ip]/l3:vrfs/vrf[name=GLOBAL]/router-bgp/neighbor[ip-address=current()/../peer-ip]/advertisement-interval";
      //n-ext:maps-to "/ac:devices/device[id=current()/../../device-ip]/l3:vrfs/vrf[name=current()/../../ivrf]/router-bgp/neighbor[ip-address=current()/../peer-ip]/advertisement-interval";
    }
    leaf time-in-sec {
      type uint16 {
        range "0..600";
      }
      description
        "0..600";
      default "5";
      n-ext:maps-to "/ac:devices/ac:device[ac:id=current()/../../device-ip]/l3:vrfs/vrf[name=current()/../../vrf]/router-bgp/neighbor[ip-address=current()/../peer-ip]/advertisement-interval";
      n-ext:maps-to "/ac:devices/ac:device[ac:id=current()/../../device-ip]/l3:vrfs/vrf[name=GLOBAL]/router-bgp/neighbor[ip-address=current()/../peer-ip]/advertisement-interval";
      n-ext:maps-to "/ac:devices/ac:device[ac:id=current()/../../device-ip]/l3:vrfs/vrf[name=current()/../../ivrf]/router-bgp/neighbor[ip-address=current()/../peer-ip]/advertisement-interval";
      when "../advertisement-interval = 'true'";
    }
    leaf timers {
      type boolean;
      description
        "timers: True/False";
    }
    leaf keepalive-interval {
      type uint16 {
        range "0..65535";
      }
      n-ext:maps-to "/ac:devices/ac:device[ac:id=current()/../../device-ip]/l3:vrfs/vrf[name=current()/../../vrf]/router-bgp/neighbor[ip-address=current()/../peer-ip]/keepalive-interval";
      n-ext:maps-to "/ac:devices/ac:device[ac:id=current()/../../device-ip]/l3:vrfs/vrf[name=GLOBAL]/router-bgp/neighbor[ip-address=current()/../peer-ip]/keepalive-interval";
      n-ext:maps-to "/ac:devices/ac:device[ac:id=current()/../../device-ip]/l3:vrfs/vrf[name=current()/../../ivrf]/router-bgp/neighbor[ip-address=current()/../peer-ip]/keepalive-interval";
      description
        "0..65535";
      default "10";
      when "../timers = 'true'";
    }
    leaf holdtime {
      type uint16 {
        range "0..65535";
      }
      n-ext:maps-to "/ac:devices/ac:device[ac:id=current()/../../device-ip]/l3:vrfs/vrf[name=current()/../../vrf]/router-bgp/neighbor[ip-address=current()/../peer-ip]/holdtime";
      n-ext:maps-to "/ac:devices/ac:device[ac:id=current()/../../device-ip]/l3:vrfs/vrf[name=GLOBAL]/router-bgp/neighbor[ip-address=current()/../peer-ip]/holdtime";
      n-ext:maps-to "/ac:devices/ac:device[ac:id=current()/../../device-ip]/l3:vrfs/vrf[name=current()/../../ivrf]/router-bgp/neighbor[ip-address=current()/../peer-ip]/holdtime";
      description
        "0..65535";
      default "30";
      when "../timers = 'true'";
    }
    leaf bfd-fall-over {
      type boolean;
      n-ext:maps-to "/ac:devices/ac:device[ac:id=current()/../../device-ip]/l3:vrfs/vrf[name=current()/../../vrf]/router-bgp/neighbor[ip-address=current()/../peer-ip]/bfd-fall-over";
      n-ext:maps-to "/ac:devices/ac:device[ac:id=current()/../../device-ip]/l3:vrfs/vrf[name=GLOBAL]/router-bgp/neighbor[ip-address=current()/../peer-ip]/bfd-fall-over";
      n-ext:maps-to "/ac:devices/ac:device[ac:id=current()/../../device-ip]/l3:vrfs/vrf[name=current()/../../ivrf]/router-bgp/neighbor[ip-address=current()/../peer-ip]/bfd-fall-over";
      description
        "Check to Enable BFD Fall-Over on Peer";
    }
  }

  grouping bgp-peer-props1 {
    description
      "Properties relating to the BGP route selection process";
    leaf peer-group {
      type string-no-space;
      description
        "peer-group";
      //n-ext:maps-to "/ac:devices/device/l3:vrfs/vrf/router-bgp/peer-group/name";
    }
    leaf peer-description {
      type string;
      description
        "string";
      //n-ext:maps-to "/ac:devices/ac:device/l3:vrfs/vrf/router-bgp/peer-group[name=current()/../peer-group]/description";
    }
    leaf listen-range {
      type inet:ipv4-prefix;
      description
        "Listen Range Prefix";
    }
    leaf remote-as {
      type inet:as-number;
      //mandatory true;
      description
        "string";
      //n-ext:maps-to "/ac:devices/device/l3:vrfs/vrf/router-bgp/neighbor/as-number";
      //n-ext:maps-to "/ac:devices/ac:device/l3:vrfs/vrf/router-bgp/peer-group[name=current()/../peer-group]/remote-as";
    }
    leaf password {
      type string-no-space;
      description
        "string";
      //n-ext:maps-to "/ac:devices/device/l3:vrfs/vrf/router-bgp/neighbor/password";
      //n-ext:maps-to "/ac:devices/ac:device/l3:vrfs/vrf/router-bgp/peer-group[name=current()/../peer-group]/password";
    }
    leaf import-route-map {
      type leafref {
        //path "../../../route-maps/route-map/route-map-name";
        path "/ac:services/cpedeployment:managed-cpe-services/customer[name=current()/../../../name]/route-maps/route-map/route-map-name";
      }
      description
        "import-route-map";
      //n-ext:maps-to "/ac:devices/device/l3:vrfs/vrf/router-bgp/neighbor/inbound-routepolicy";
      //n-ext:maps-to "/ac:devices/ac:device/l3:vrfs/vrf/router-bgp/peer-group[name=current()/../peer-group]/in-route-map";
    }
    leaf export-route-map {
      type leafref {
        //path "../../../route-maps/route-map/route-map-name";
        path "/ac:services/cpedeployment:managed-cpe-services/customer[name=current()/../../../name]/route-maps/route-map/route-map-name";
      }
      description
        "export-route-map";
      //n-ext:maps-to "/ac:devices/device/l3:vrfs/vrf/router-bgp/neighbor/outbound-routepolicy";
      //n-ext:maps-to "/ac:devices/ac:device/l3:vrfs/vrf/router-bgp/peer-group[name=current()/../peer-group]/out-route-map";
    }
    leaf next-hop-self {
      type boolean;
      description
        "next-hop-self: True/False";
      //n-ext:maps-to "/ac:devices/device/l3:vrfs/vrf/router-bgp/neighbor/next-hop-self";
      //n-ext:maps-to "/ac:devices/ac:device/l3:vrfs/vrf/router-bgp/peer-group[name=current()/../peer-group]/next-hop-self";
    }
    leaf soft-reconfiguration {
      type boolean;
      description
        "soft-reconfiguration: True/False";
      //n-ext:maps-to "/ac:devices/device/l3:vrfs/vrf/router-bgp/neighbor/soft-reconfiguration";
      //n-ext:maps-to "/ac:devices/ac:device/l3:vrfs/vrf/router-bgp/peer-group[name=current()/../peer-group]/soft-reconfiguration";
    }
    leaf default-originate {
      type boolean;
      description
        "default-originate: True/False";
      //n-ext:maps-to "/ac:devices/device/l3:vrfs/vrf/router-bgp/neighbor/default-originate";
      //n-ext:maps-to "/ac:devices/ac:device/l3:vrfs/vrf/router-bgp/peer-group[name=current()/../peer-group]/default-originate";
    }
    leaf default-originate-route-map {
      type leafref {
        //path "../../../route-maps/route-map/route-map-name";
        path "/ac:services/cpedeployment:managed-cpe-services/customer[name=current()/../../../name]/route-maps/route-map/route-map-name";
      }
      description
        "default-originate-route-map";
      when "../default-originate = 'true'";
      //n-ext:maps-to "/ac:devices/device/l3:vrfs/vrf/router-bgp/neighbor/def-originate-route-map";
      //n-ext:maps-to "/ac:devices/ac:device/l3:vrfs/vrf/router-bgp/peer-group[name=current()/../peer-group]/def-originate-route-map";
    }
    leaf send-community {
      type boolean;
      description
        "send-community: True/False";
      //n-ext:maps-to "/ac:devices/device/l3:vrfs/vrf/router-bgp/neighbor/send-community";
      //n-ext:maps-to "/ac:devices/ac:device/l3:vrfs/vrf/router-bgp/peer-group[name=current()/../peer-group]/send-community";
    }
    leaf as-override {
      type boolean;
      description
        "Check to enable as-override";
    }
    leaf encrypted-password {
      type boolean;
      description
        "encrypted-password: True/False";
      //n-ext:maps-to "/ac:devices/device/l3:vrfs/vrf/router-bgp/neighbor/encryption";
      //n-ext:maps-to "/ac:devices/ac:device/l3:vrfs/vrf/router-bgp/peer-group[name=current()/../peer-group]/encryption";
      config false;
    }
    leaf advertisement-interval {
      type boolean;
      description
        "advertisement-interval: True/False";
      //n-ext:maps-to "/ac:devices/ac:device/l3:vrfs/vrf/router-bgp/peer-group[name=current()/../peer-group]/advertisement-interval";
    }
    leaf time-in-sec {
      type uint16 {
        range "0..600";
      }
      description
        "0..600";
      default "5";
      when "../advertisement-interval = 'true'";
    }
    leaf timers {
      type boolean;
      description
        "timers: True/False";
    }
    leaf keepalive-interval {
      type uint16 {
        range "0..65535";
      }
      //n-ext:maps-to "/ac:devices/ac:device/l3:vrfs/vrf/router-bgp/peer-group[name=current()/../peer-group]/keepalive-interval";
      description
        "0..65535";
      default "10";
      when "../timers = 'true'";
    }
    leaf holdtime {
      type uint16 {
        range "0..65535";
      }
      //n-ext:maps-to "/ac:devices/ac:device/l3:vrfs/vrf/router-bgp/peer-group[name=current()/../peer-group]/holdtime";
      description
        "0..65535";
      default "30";
      when "../timers = 'true'";
    }
    leaf ebgp-multihop {
      type uint8;
      description
        "Enter eBGP Multi-Hop Value";
    }
    leaf update-source {
      type string-no-lead-trail-space;
      description
        "Enter eBGP Peering Source Interface";
    }
  }

  grouping end-point-props {
    leaf endpoint-name {
      type string-no-space;
      description
        "string";
    }
    leaf device-ip {
      type leafref {
        path "/rp:resource-pools/rp:resource-pool[rp:name=current()/../../../resource-pool]/rp:device/rp:id";
      }
      description
        "device-ip";
      mandatory true;
    }
    leaf vrf {
      description
        "vrf";
      type leafref {
        //path "../../../../../vrfs/vrf/vrf-name";
        path "/ac:services/cpedeployment:managed-cpe-services/customer[name=current()/../../../../../name]/vrfs/vrf/vrf-name";
      }
      n-ext:maps-to "/ac:devices/ac:device[ac:id=current()/../device-ip]/if:interfaces/interface[long-name=current()/../interface-name]/vrf";
      when "../interface-type =  'Physical' or ../interface-type =  'Sub-Interface' or ../interface-type =  'SVI'";
    }
    leaf interface-type {
      type interface-type;
      description
        "Physical
         Sub-Interface
        ";
      //n-ext:maps-to "/ac:devices/device/if:interfaces/interface/mode";
      mandatory true;
    }
    leaf interface-name {
      type leafref {
        path "/ac:devices/ac:device[ac:id=current()/../device-ip]/if:interfaces/if:interface/if:name";
      }
      description
        "interface-name";
      n-ext:maps-to "/ac:devices/ac:device[ac:id=current()/../device-ip]/if:interfaces/interface/name";
      //mandatory true;
      when "../interface-type =  'Physical' or ../interface-type =  'Sub-Interface'";
    }
    leaf vlan-id {
      type uint32 {
        range "1..4096";
      }
      n-ext:maps-to "/ac:devices/ac:device[ac:id=current()/../device-ip]/if:interfaces/interface[long-name=current()/../interface-name]/l3:vlan";
      description
        "1..4096";
      when "../interface-type =  'Sub-Interface' or ../interface-type =  'SVI'";
    }
    leaf interface-ip {
      type inet:ipv4-address;
      description
        "Valid IPv4 Address (A.B.C.D for e.x: 172.16.1.1)";
      //mandatory true;
      n-ext:maps-to "/ac:devices/ac:device[ac:id=current()/../device-ip]/if:interfaces/interface[long-name=current()/../interface-name]/ip-address";
    }
    leaf interface-description {
      type string-no-lead-trail-space;
      description
        "string";
      n-ext:maps-to "/ac:devices/ac:device[ac:id=current()/../device-ip]/if:interfaces/interface[long-name=current()/../interface-name]/description";
    }
    leaf pbr-policy {
      type leafref {
        path "/ac:services/cpedeployment:managed-cpe-services/customer[name=current()/../../../../../name]/route-maps/route-map/route-map-name";
      }
      n-ext:maps-to "/ac:devices/ac:device[ac:id=current()/../device-ip]/if:interfaces/interface[long-name=current()/../interface-name]/pbr-policy";
      description
        "Select PBR Policy to apply on interface";
    }
    leaf mace-enable {
      type boolean;
      description
        "enabling mace-enable for interface";
      n-ext:maps-to "/ac:devices/ac:device[ac:id=current()/../device-ip]/if:interfaces/interface[long-name=current()/../interface-name]/mace-enable";
    }
    leaf dps {
      type boolean;
      description
        "Check if DPS Controller LAN Interface";
      when "../interface-type =  'Physical' or ../interface-type =  'Sub-Interface' or ../interface-type =  'SVI'";
    }
    leaf tcp-mss {
      type uint16 {
        range "500..1460";
      }
      description
        "Interface TCP Adjust MSS";
      n-ext:maps-to "/ac:devices/ac:device[ac:id=current()/../device-ip]/if:interfaces/interface[long-name=current()/../interface-name]/maximum-segment-size";
    }
    leaf bandwidth {
      type uint32 {
        range "1..100000000";
      }
      description
        "Enter Interface Bandwidth";
      n-ext:maps-to "/ac:devices/ac:device[ac:id=current()/../device-ip]/if:interfaces/interface[long-name=current()/../interface-name]/bandwidth";
    }
    leaf ospf {
      type boolean;
      description
        "Check to enable OSPF. The LAN interface IP address/Mask will be added in OSPF process network statement";
      when "../interface-type =  'Physical' or ../interface-type =  'Sub-Interface' or ../interface-type =  'SVI'";
    }
    leaf priority {
      type uint32 {
        range "0..255";
      }
      description
        "Enter OSPF Interface Priority";
      n-ext:maps-to "/ac:devices/ac:device[ac:id=current()/../device-ip]/if:interfaces/interface[long-name=current()/../interface-name]/ospf/priority";
      when "../ospf = 'true'";
    }
    leaf cost {
      type uint32 {
        range "1..65535";
      }
      description
        "Enter OSPF Interface Cost";
      n-ext:maps-to "/ac:devices/ac:device[ac:id=current()/../device-ip]/if:interfaces/interface[long-name=current()/../interface-name]/ospf/cost";
      when "../ospf = 'true'";
    }
    leaf fast-hello {
      type boolean;
      description
        "Check to enable OSPF Fast Hello";
      when "../ospf = 'true'";
    }
    leaf hello-multiplier {
      type uint8 {
        range "3..20";
      }
      description
        "Enter OSPF Fast Hello Multiplier";
      n-ext:maps-to "/ac:devices/ac:device[ac:id=current()/../device-ip]/if:interfaces/interface[long-name=current()/../interface-name]/ospf/hello-multiplier";
      when "../ospf = 'true' and ../fast-hello = 'true'";
    }
    leaf hello-interval {
      type uint32 {
        range "1..65535";
      }
      description
        "Enter OSPF Adjacency Hello Interval Timer";
      n-ext:maps-to "/ac:devices/ac:device[ac:id=current()/../device-ip]/if:interfaces/interface[long-name=current()/../interface-name]/ospf/hello-interval";
      when "../ospf = 'true' and ../fast-hello = 'false'";
    }
    leaf dead-interval {
      type uint32 {
        range "1..65535";
      }
      description
        "Enter OSPF Adjacency Dead Interval Timer";
      n-ext:maps-to "/ac:devices/ac:device[ac:id=current()/../device-ip]/if:interfaces/interface[long-name=current()/../interface-name]/ospf/dead-interval";
      when "../ospf = 'true' and ../fast-hello = 'false'";
    }
    leaf ospf-id {
      type uint16;
      description
        "Enter OSPF Process ID";
      //n-ext:maps-to "/ac:devices/ac:device[ac:id=current()/../device-ip]/if:interfaces/interface[long-name=current()/../interface-name]/ospf/ospf-id";
      n-ext:maps-to "/ac:devices/ac:device[ac:id=current()/../device-ip]/l3:vrfs/l3:vrf[name=GLOBAL]/router-ospf/process-id";
      n-ext:maps-to "/ac:devices/ac:device[ac:id=current()/../device-ip]/l3:vrfs/l3:vrf[name=current()/../vrf]/router-ospf/process-id";
      when "../ospf = 'true'";
    }
    leaf area {
      type union {
        type uint32;
        type inet:ipv4-address;
      }
      description
        "Enter OSPF Area ID";
      //n-ext:maps-to "/ac:devices/ac:device[ac:id=current()/../device-ip]/if:interfaces/interface[long-name=current()/../interface-name]/ospf/area";
      n-ext:maps-to "/ac:devices/ac:device[ac:id=current()/../device-ip]/l3:vrfs/l3:vrf[name=GLOBAL]/router-ospf[process-id=current()/../ospf-id]/network/area";
      n-ext:maps-to "/ac:devices/ac:device[ac:id=current()/../device-ip]/l3:vrfs/l3:vrf[name=current()/../vrf]/router-ospf[process-id=current()/../ospf-id]/network/area";
      when "../ospf = 'true'";
    }
    leaf inbound-acl {
      type boolean;
      description
        "Check to configure inbound ACL on interface";
      when "../interface-type =  'Physical' or ../interface-type =  'Sub-Interface' or ../interface-type =  'SVI'";
    }
    leaf global-inbound-acl {
      type leafref {
        path "/ac:services/cpedeployment:managed-cpe-services/customer[name=current()/../../../../../name]/access-lists/access-list/name";
      }
      description
        "Select Inbound ACL Name configured at the customer level";
      when "../inbound-acl = 'true'";
      //n-ext:maps-to "/ac:devices/device[id=current()/../device-ip]/acl:access-lists/access-list/name";
      n-ext:maps-to "/ac:devices/ac:device[ac:id=current()/../device-ip]/if:interfaces/interface[long-name=current()/../interface-name]/acl-inbound-name";
    }
    leaf site-inbound-acl {
      type string-no-space;
      description
        "Enter Inbound ACL Name configured at the site level";
      when "../inbound-acl = 'true'";
      //n-ext:maps-to "/ac:devices/device[id=current()/../device-ip]/acl:access-lists/access-list/name";
      n-ext:maps-to "/ac:devices/ac:device[ac:id=current()/../device-ip]/if:interfaces/interface[long-name=current()/../interface-name]/acl-inbound-name";
    }
    leaf outbound-acl {
      type boolean;
      description
        "Check to configure outbound ACL on interface";
      when "../interface-type =  'Physical' or ../interface-type =  'Sub-Interface' or ../interface-type =  'SVI'";
    }
    leaf global-outbound-acl {
      type leafref {
        path "/ac:services/cpedeployment:managed-cpe-services/customer[name=current()/../../../../../name]/access-lists/access-list/name";
      }
      description
        "Select Outbound ACL Name configured at the customer level";
      when "../outbound-acl = 'true'";
      //n-ext:maps-to "/ac:devices/device[id=current()/../device-ip]/acl:access-lists/access-list/name";
      n-ext:maps-to "/ac:devices/ac:device[ac:id=current()/../device-ip]/if:interfaces/interface[long-name=current()/../interface-name]/acl-outbound-name";
    }
    leaf site-outbound-acl {
      type string-no-space;
      description
        "Enter Outbound ACL Name configured at the site level";
      //n-ext:maps-to "/ac:devices/device[id=current()/../device-ip]/acl:access-lists/access-list/name";
      n-ext:maps-to "/ac:devices/ac:device[ac:id=current()/../device-ip]/if:interfaces/interface[long-name=current()/../interface-name]/acl-outbound-name";
      when "../outbound-acl = 'true'";
    }
    leaf nat-inside {
      type boolean;
      description
        "Check to configure interface as NAT inside direction";
      when "../interface-type =  'Physical' or ../interface-type =  'Sub-Interface' or ../interface-type =  'Tunnel' or ../interface-type =  'SVI'";
    }
    leaf nat-outside {
      type boolean;
      description
        "Check to configure interface as NAT outside direction";
      when "../interface-type =  'Physical' or ../interface-type =  'Sub-Interface' or ../interface-type =  'Tunnel' or ../interface-type =  'SVI'";
    }
    leaf nbar-discovery {
      type enumeration {
        enum "protocol-discovery";
        enum "protocol-discovery ipv4";
        enum "protocol-discovery ipv6";
      }
      description
        "Enable NBAR Protocol Discovery";
      n-ext:maps-to "/ac:devices/ac:device[ac:id=current()/../device-ip]/if:interfaces/interface[long-name=current()/../interface-name]/if-ext:protocol-discovery";
    }
    leaf delay {
      type uint32 {
        range "1..16777215";
      }
      description
        "1..16777215";
      when "../interface-type =  'Physical' or ../interface-type =  'Sub-Interface' or ../interface-type =  'SVI'";
    }
    leaf bfd {
      type boolean;
      description
        "Check to Configure BFD on Interface";
    }
    leaf bfd-interval {
      type uint16 {
        range "50..999";
      }
      description
        "Enter Transmit interval between BFD packets (milliseconds)";
      when "../bfd = 'true'";
      n-ext:maps-to "/ac:devices/ac:device[ac:id=current()/../device-ip]/if:interfaces/interface[long-name=current()/../interface-name]/if-ext:interval";
    }
    leaf bfd-min-rx {
      type uint16 {
        range "50..999";
      }
      description
        "Enter Transmit interval between BFD packets (milliseconds)";
      when "../bfd = 'true'";
      n-ext:maps-to "/ac:devices/ac:device[ac:id=current()/../device-ip]/if:interfaces/interface[long-name=current()/../interface-name]/if-ext:min_rx";
    }
    leaf bfd-multiplier {
      type uint8 {
        range "3..50";
      }
      description
        "Multiplier value used to compute holddown";
      when "../bfd = 'true'";
      n-ext:maps-to "/ac:devices/ac:device[ac:id=current()/../device-ip]/if:interfaces/interface[long-name=current()/../interface-name]/if-ext:multiplier";
    }
    list dhcp-helper-addresses {
      key "helper-address";
      leaf sequence-number {
        type string;
        description
          "string";
        default "200";
        config false;
      }
      leaf helper-address {
        type inet:ipv4-address;
        description
          "Enter DHCP Helper IPv4 Address";
        n-ext:maps-to "/ac:devices/ac:device[ac:id=current()/../device-ip]/if:interfaces/interface[long-name=current()/../interface-name]/if-ext:helper-address/if-ext:helper/if-ext:dest-address";
      }
      leaf vrf {
        type leafref {
          path "/ac:services/cpedeployment:managed-cpe-services/customer[name=current()/../../../../../../name]/vrfs/vrf/vrf-name";
          require-instance false;
        }
        description
          "Enter DHCP Helper VRF";
        n-ext:maps-to "/ac:devices/ac:device[ac:id=current()/../device-ip]/if:interfaces/interface[long-name=current()/../interface-name]/if-ext:helper-address/if-ext:helper[if-ext:dest-address=current()/../helper-address]/if-ext:vrf";
      }
    }
  }

  grouping end-point-props2 {
    leaf endpoint-name {
      type string-no-space;
      description
        "Enter Endpoint Name
         This is an internal field for Anuta NCX
        ";
    }
    leaf device-ip {
      type leafref {
        path "/rp:resource-pools/rp:resource-pool[rp:name=current()/../../../resource-pool]/rp:device/rp:id";
      }
      description
        "Select Device Hostname";
      mandatory true;
    }
    leaf vrf {
      description
        "vrf";
      type leafref {
        //path "../../../../../vrfs/vrf/vrf-name";
        path "/ac:services/cpedeployment:managed-cpe-services/customer[name=current()/../../../../../name]/vrfs/vrf/vrf-name";
      }
      n-ext:maps-to "/ac:devices/ac:device[ac:id=current()/../device-ip]/if:interfaces/interface[long-name=current()/../interface-name]/vrf";
      when "../interface-type =  'Physical' or ../interface-type =  'Sub-Interface' or ../interface-type = 'SVI'";
    }
    leaf interface-type {
      type interface-type;
      description
        "Physical
         Sub-Interface
        ";
      //n-ext:maps-to "/ac:devices/device/if:interfaces/interface/mode";
      mandatory true;
    }
    leaf interface-name {
      type leafref {
        path "/ac:devices/ac:device[ac:id=current()/../device-ip]/if:interfaces/if:interface/if:name";
      }
      description
        "interface-name";
      n-ext:maps-to "/ac:devices/ac:device[ac:id=current()/../device-ip]/if:interfaces/interface/name";
      //mandatory true;
      when "../interface-type =  'Physical' or ../interface-type =  'Sub-Interface'";
    }
    leaf vlan-id {
      type uint32 {
        range "1..4096";
      }
      n-ext:maps-to "/ac:devices/ac:device[ac:id=current()/../device-ip]/if:interfaces/interface[long-name=current()/../interface-name]/vlan";
      description
        "1..4096";
      when "../interface-type =  'Sub-Interface' or ../interface-type =  'SVI'";
    }
    leaf interface-ip {
      type inet:ipv4-address;
      description
        "Valid IPv4 Address (A.B.C.D for e.x: 172.16.1.1)";
      n-ext:maps-to "/ac:devices/ac:device[ac:id=current()/../device-ip]/if:interfaces/interface[long-name=current()/../interface-name]/ip-address";
    }
    leaf interface-description {
      type string-no-lead-trail-space;
      description
        "string";
      n-ext:maps-to "/ac:devices/ac:device[ac:id=current()/../device-ip]/if:interfaces/interface[long-name=current()/../interface-name]/description";
    }
    leaf mace-enable {
      type boolean;
      description
        "enabling mace-enable for interface";
      n-ext:maps-to "/ac:devices/ac:device[ac:id=current()/../device-ip]/if:interfaces/interface[long-name=current()/../interface-name]/mace-enable";
    }
    leaf inbound-acl {
      type boolean;
      description
        "Check to configure inbound ACL on interface";
      when "../interface-type =  'Physical' or ../interface-type =  'Sub-Interface'";
    }
    leaf global-inbound-acl {
      type leafref {
        path "/ac:services/cpedeployment:managed-cpe-services/customer[name=current()/../../../../../name]/access-lists/access-list/name";
      }
      description
        "Select Inbound ACL Name configured at the customer level";
      when "../inbound-acl = 'true'";
      n-ext:maps-to "/ac:devices/ac:device[ac:id=current()/../device-ip]/if:interfaces/interface[long-name=current()/../interface-name]/acl-inbound-name";
    }
    leaf site-inbound-acl {
      type string-no-space;
      description
        "Enter Inbound ACL Name configured at the site level";
      when "../inbound-acl = 'true'";
      n-ext:maps-to "/ac:devices/ac:device[ac:id=current()/../device-ip]/if:interfaces/interface[long-name=current()/../interface-name]/acl-inbound-name";
    }
    leaf outbound-acl {
      type boolean;
      description
        "Check to configure outbound ACL on interface";
      when "../interface-type =  'Physical' or ../interface-type =  'Sub-Interface'";
    }
    leaf global-outbound-acl {
      type leafref {
        path "/ac:services/cpedeployment:managed-cpe-services/customer[name=current()/../../../../../name]/access-lists/access-list/name";
      }
      description
        "Select Outbound ACL Name configured at the customer level";
      when "../outbound-acl = 'true'";
      n-ext:maps-to "/ac:devices/ac:device[ac:id=current()/../device-ip]/if:interfaces/interface[long-name=current()/../interface-name]/acl-outbound-name";
    }
    leaf site-outbound-acl {
      type string-no-space;
      description
        "Enter Outbound ACL Name configured at the site level";
      when "../outbound-acl = 'true'";
      n-ext:maps-to "/ac:devices/ac:device[ac:id=current()/../device-ip]/if:interfaces/interface[long-name=current()/../interface-name]/acl-outbound-name";
    }
    leaf pbr-policy {
      type leafref {
        path "../../../../../route-maps/route-map/route-map-name";
      }
      description
        "Select PBR Policy to apply on interface";
      n-ext:maps-to "/ac:devices/ac:device[ac:id=current()/../device-ip]/if:interfaces/interface[long-name=current()/../interface-name]/pbr-policy";
    }
    leaf nat-inside {
      type boolean;
      description
        "Check to configure interface as NAT inside direction";
      when "../interface-type =  'Physical' or ../interface-type =  'Sub-Interface' or ../interface-type =  'Tunnel'";
    }
    leaf nat-outside {
      type boolean;
      description
        "Check to configure interface as NAT outside direction";
      when "../interface-type =  'Physical' or ../interface-type =  'Sub-Interface' or ../interface-type =  'Tunnel'";
    }
    leaf dps {
      type boolean;
      description
        "
         Check if the endpoint is a DPS B2B interface
        ";
      default "false";
    }
    leaf delay {
      type uint32 {
        range "1..16777215";
      }
      description
        "1..16777215";
      when "../interface-type =  'Physical' or ../interface-type =  'Sub-Interface'";
    }
  }

  grouping end-point-props1 {
    leaf endpoint-name {
      type string-no-space;
      description
        "Enter Endpoint Name
         This is an internal field for Anuta NCX
        ";
    }
    leaf device-ip {
      type leafref {
        path "/rp:resource-pools/rp:resource-pool[rp:name=current()/../../../resource-pool]/rp:device/rp:id";
      }
      description
        "Select Device Hostname";
      mandatory true;
    }
    leaf fvrf {
      type union {
        type leafref {
          //path "../../../../../vrfs/vrf/vrf-name";
          path "/ac:services/cpedeployment:managed-cpe-services/customer[name=current()/../../../../../name]/vrfs/vrf/vrf-name";
          require-instance false;
        }
        type string-no-space;
      }
      description
        "Select Front-End VRF Name
         The FVRF will configure tunnel vrf under the Tunnel Interface
        ";
      //n-ext:maps-to "/ac:devices/device[id=current()/../device-ip]/if:interfaces/interface[long-name=current()/../interface-name]/l3:vrf";
      n-ext:maps-to "/ac:devices/ac:device[ac:id=current()/../device-ip]/dmvpn:dmvpntunnels/dmvpntunnel[name=current()/../tunnel-interface-id]/front-vrf-name";
      when "../interface-type =  'Tunnel'";
    }
    leaf ivrf {
      type leafref {
        //path "../../../../../vrfs/vrf/vrf-name";
        path "/ac:services/cpedeployment:managed-cpe-services/customer[name=current()/../../../../../name]/vrfs/vrf/vrf-name";
      }
      description
        "Select Inside VRF Name
         The IVRF will configure ip vrf forwarding under the Tunnel Interface
        ";
      //n-ext:maps-to "/ac:devices/device[id=current()/../device-ip]/if:interfaces/interface[long-name=current()/../interface-name]/l3:vrf";
      n-ext:maps-to "/ac:devices/ac:device[ac:id=current()/../device-ip]/dmvpn:dmvpntunnels/dmvpntunnel[name=current()/../tunnel-interface-id]/vrf-name";
      when "../interface-type =  'Tunnel'";
    }
    leaf vrf {
      description
        "vrf";
      type leafref {
        //path "../../../../../vrfs/vrf/vrf-name";
        path "/ac:services/cpedeployment:managed-cpe-services/customer[name=current()/../../../../../name]/vrfs/vrf/vrf-name";
      }
      n-ext:maps-to "/ac:devices/ac:device[ac:id=current()/../device-ip]/if:interfaces/interface[long-name=current()/../interface-name]/l3:vrf";
      when "../interface-type =  'Physical' or ../interface-type =  'Sub-Interface'";
    }
    leaf interface-type {
      type interface-type1;
      description
        "Physical
         Sub-Interface
        ";
      //      n-ext:maps-to "/ac:devices/device/if:interfaces/interface/mode";
      mandatory true;
    }
    leaf interface-name {
      type leafref {
        path "/ac:devices/ac:device[ac:id=current()/../device-ip]/if:interfaces/if:interface/if:name";
      }
      description
        "interface-name";
      n-ext:maps-to "/ac:devices/ac:device[ac:id=current()/../device-ip]/if:interfaces/if:interface/if:name";
      //mandatory true;
      when "../interface-type =  'Physical' or ../interface-type =  'Sub-Interface'";
    }
    leaf vlan-id {
      type uint32 {
        range "1..4096";
      }
      n-ext:maps-to "/ac:devices/ac:device[ac:id=current()/../device-ip]/if:interfaces/interface[long-name=current()/../interface-name]/l3:vlan";
      description
        "1..4096";
      when "../interface-type =  'Sub-Interface' or ../interface-type =  'SVI'";
    }
    leaf interface-ip {
      type inet:ipv4-address;
      description
        "Valid IPv4 Address (A.B.C.D for e.x: 172.16.1.1)";
      config false;
      n-ext:maps-to "/ac:devices/ac:device[ac:id=current()/../device-ip]/if:interfaces/interface[long-name=current()/../interface-name]/ip-address";
    }
    leaf interface-description {
      type string-no-lead-trail-space;
      description
        "string";
      n-ext:maps-to "/ac:devices/ac:device[ac:id=current()/../device-ip]/if:interfaces/interface[long-name=current()/../interface-name]/description";
      n-ext:maps-to "/ac:devices/ac:device[ac:id=current()/../device-ip]/dmvpn:dmvpntunnels/dmvpntunnel[name=current()/../tunnel-interface-id]/description";
    }
    leaf mace-enable {
      type boolean;
      description
        "enabling mace-enable for interface";
      n-ext:maps-to "/ac:devices/ac:device[ac:id=current()/../device-ip]/if:interfaces/interface[long-name=current()/../interface-name]/mace-enable";
    }
    leaf inbound-acl {
      type boolean;
      description
        "Check to configure inbound ACL on interface";
      when "../interface-type =  'Physical' or ../interface-type =  'Sub-Interface'";
    }
    leaf global-inbound-acl {
      type leafref {
        path "/ac:services/cpedeployment:managed-cpe-services/customer[name=current()/../../../../../name]/access-lists/access-list/name";
      }
      description
        "Select Inbound ACL Name configured at the customer level";
      when "../inbound-acl = 'true'";
      //n-ext:maps-to "/ac:devices/device[id=current()/../device-ip]/acl:access-lists/access-list/name";
      n-ext:maps-to "/ac:devices/ac:device[ac:id=current()/../device-ip]/if:interfaces/interface[long-name=current()/../interface-name]/acl-inbound-name";
    }
    leaf site-inbound-acl {
      type string-no-space;
      description
        "Enter Inbound ACL Name configured at the site level";
      when "../inbound-acl = 'true'";
      //n-ext:maps-to "/ac:devices/device[id=current()/../device-ip]/acl:access-lists/access-list/name";
      n-ext:maps-to "/ac:devices/ac:device[ac:id=current()/../device-ip]/if:interfaces/interface[long-name=current()/../interface-name]/acl-inbound-name";
    }
    leaf outbound-acl {
      type boolean;
      description
        "Check to configure outbound ACL on interface";
      when "../interface-type =  'Physical' or ../interface-type =  'Sub-Interface'";
    }
    leaf global-outbound-acl {
      type leafref {
        path "/ac:services/cpedeployment:managed-cpe-services/customer[name=current()/../../../../../name]/access-lists/access-list/name";
      }
      description
        "Select Outbound ACL Name configured at the customer level";
      //n-ext:maps-to "/ac:devices/device[id=current()/../device-ip]/acl:access-lists/access-list/name";
      n-ext:maps-to "/ac:devices/ac:device[ac:id=current()/../device-ip]/if:interfaces/interface[long-name=current()/../interface-name]/acl-outbound-name";
      when "../outbound-acl = 'true'";
    }
    leaf site-outbound-acl {
      type string-no-space;
      description
        "Enter Outbound ACL Name configured at the site level";
      when "../outbound-acl = 'true'";
      //n-ext:maps-to "/ac:devices/device[id=current()/../device-ip]/acl:access-lists/access-list/name";
      n-ext:maps-to "/ac:devices/ac:device[ac:id=current()/../device-ip]/if:interfaces/interface[long-name=current()/../interface-name]/acl-outbound-name";
    }
    leaf nat-inside {
      type boolean;
      description
        "Check to configure interface as NAT inside direction";
      when "../interface-type =  'Physical' or ../interface-type =  'Sub-Interface' or ../interface-type =  'Tunnel'";
    }
    leaf nat-outside {
      type boolean;
      description
        "Check to configure interface as NAT outside direction";
      when "../interface-type =  'Physical' or ../interface-type =  'Sub-Interface' or ../interface-type =  'Tunnel'";
    }
    leaf wan-interface-bandwidth {
      type uint32 {
        range "1..100000000";
      }
      description
        "Enter WAN Interface Bandwidth in Kbits/sec";
      when "../interface-type =  'Physical' or ../interface-type =  'Sub-Interface'  or ../interface-type =  'SVI' ";
      n-ext:maps-to "/ac:devices/ac:device[ac:id=current()/../device-ip]/if:interfaces/interface[long-name=current()/../interface-name]/bandwidth";
    }
    leaf delay {
      type uint32 {
        range "1..16777215";
      }
      description
        "1..16777215";
      when "../interface-type =  'Physical' or ../interface-type =  'Sub-Interface'";
    }
    leaf pbr-policy {
      type leafref {
        path "/ac:services/cpedeployment:managed-cpe-services/customer[name=current()/../../../../../name]/route-maps/route-map/route-map-name";
      }
      //n-ext:maps-to "/ac:devices/ac:device[ac:id=current()/../device-ip]/if:interfaces/interface[long-name=current()/../interface-name]/pbr-policy";
      n-ext:maps-to "/ac:devices/ac:device[ac:id=current()/../device-ip]/l3features:route-maps/route-map/name";
      description
        "Select PBR Policy to apply on interface";
      when "../interface-type =  'Tunnel'";
    }
    leaf bfd {
      type boolean;
      description
        "Check to Configure BFD on Interface";
    }
    leaf bfd-interval {
      type uint16 {
        range "50..999";
      }
      description
        "Enter Transmit interval between BFD packets (milliseconds)";
      when "../bfd = 'true'";
      n-ext:maps-to "/ac:devices/ac:device[ac:id=current()/../device-ip]/if:interfaces/interface[long-name=current()/../interface-name]/if-ext:interval";
    }
    leaf bfd-min-rx {
      type uint16 {
        range "50..999";
      }
      description
        "Enter BFD Minimum Receive Interval Capability (milliseconds)";
      when "../bfd = 'true'";
      n-ext:maps-to "/ac:devices/ac:device[ac:id=current()/../device-ip]/if:interfaces/interface[long-name=current()/../interface-name]/if-ext:min_rx";
    }
    leaf bfd-multiplier {
      type uint8 {
        range "3..50";
      }
      description
        "Multiplier value used to compute holddown";
      when "../bfd = 'true'";
      n-ext:maps-to "/ac:devices/ac:device[ac:id=current()/../device-ip]/if:interfaces/interface[long-name=current()/../interface-name]/if-ext:multiplier";
    }
  }

  grouping ic-local-props {
    description
      "subnetwork properties";
    leaf cidr {
      type inet:ipv4-prefix;
      //type leafref {
      //  path "/ip:ipaddress-pools/ip:ipaddress-pool/ip:cidr";
      //}
      description
        "cidr";
      mandatory true;
    }
    leaf inbound-policy {
      type leafref {
        path "/ac:services/cpedeployment:managed-cpe-services/customer[name=current()/../../../../name]/qos-service/policies/policy/name";
      }
      description
        "inbound-policy";
      //n-ext:maps-to "/ac:devices/device/if:interfaces/interface/inbound-qos";
      n-ext:maps-to "/ac:devices/ac:device/qos:policy-maps/policy-map/name";
    }
    leaf hierarchical-outbound-policy {
      type boolean;
      description
        "hierarchical-outbound-policy: True/False";
    }
    leaf outbound-policy {
      type leafref {
        path "/ac:services/cpedeployment:managed-cpe-services/customer[name=current()/../../../../name]/qos-service/policies/policy/name";
      }
      description
        "outbound-policy";
      when "../hierarchical-outbound-policy = 'false'";
      //n-ext:maps-to "/ac:devices/device[id=current()/../../../../name]/if:interfaces/interface/outbound-qos";
      n-ext:maps-to "/ac:devices/ac:device/qos:policy-maps/policy-map/name";
    }
    leaf policy-name {
      type string-no-space;
      description
        "string";
      when "../hierarchical-outbound-policy = 'true'";
      n-ext:maps-to "/ac:devices/ac:device/qos:policy-maps/policy-map/name";
    }
    leaf shape-average {
      type uint64 {
        range "8000..10000000000";
      }
      description
        "8000..10000000000";
      when "../hierarchical-outbound-policy = 'true'";
      n-ext:maps-to "/ac:devices/ac:device/qos:policy-maps/policy-map[name=current()/../name]/class-entry/shape-average";
    }
    leaf bits-sustained {
      type uint64 {
        range "32..800000000";
      }
      description
        "Enter Shaper Bc Value";
      when "../hierarchical-outbound-policy = 'true'";
      n-ext:maps-to "/ac:devices/ac:device/qos:policy-maps/policy-map[name=current()/../name]/class-entry/bits-sustained";
    }
    leaf bits-excess {
      type uint64 {
        range "0..154400000";
      }
      description
        "Enter Shaper Be Value";
      when "../hierarchical-outbound-policy = 'true'";
      n-ext:maps-to "/ac:devices/ac:device/qos:policy-maps/policy-map[name=current()/../name]/class-entry/bits-excess";
    }
    leaf child-qos-policy {
      type leafref {
        path "/ac:services/cpedeployment:managed-cpe-services/customer[name=current()/../../../../name]/qos-service/policies/policy/name";
      }
      description
        "child-qos-policy";
      n-ext:maps-to "/ac:devices/ac:device/qos:policy-maps/policy-map[name=current()/../name]/class-entry/service-policy";
      when "../hierarchical-outbound-policy = 'true'";
    }
    leaf class-entry {
      type boolean;
      description
        "class-entry: True/False";
      when "../hierarchical-outbound-policy = 'true'";
      config false;
    }
    leaf hierarchical-policy {
      type leafref {
        path "/ac:services/cpedeployment:managed-cpe-services/customer[name=current()/../../../../name]/qos-service/hierarchical-policy/policy/name";
      }
      description
        "hierarchical-policy";
      when "../hierarchical-outbound-policy = 'true' and ../class-entry = 'true'";
      config false;
    }
    leaf auto-negotiation {
      type boolean;
      description
        "auto-negotiation: True/False";
      default "false";
    }
    leaf speed {
      type enumeration {
        enum "10";
        enum "100";
        enum "1000";
        enum "10000";
      }
      description
        "Speed in Mbps, Example: 10, 100, 1000, auto";
      when "../auto-negotiation = 'false'";
      //      n-ext:maps-to "/ac:devices/device/InfSpeedAndDuplex/speed";
      //n-ext:maps-to "/ac:devices/ac:device/if:interfaces/interface/link-speed";
    }
    leaf duplex {
      type enumeration {
        enum "half";
        enum "full";
        enum "auto";
      }
      description
        "Duplex options, 'auto' or 'full' or 'half' ";
      when "../auto-negotiation = 'false'";
      //      n-ext:maps-to "/ac:devices/device/InfSpeedAndDuplex/duplex";
      //n-ext:maps-to "/ac:devices/ac:device/if:interfaces/interface/duplex";
    }
    leaf load-interval {
      type boolean;
      description
        "load-interval: True/False";
    }
    leaf load-interval-delay {
      type uint16 {
        range "30 | 60 | 90 | 120 | 150 | 180 | 210 | 240 | 270 | 300 | 330 | 360 | 390 | 420 | 450 | 480 | 510 | 540 | 570 | 600";
      }
      description
        "Range in between 30 to 600 and Load interval must be in increments of 30 seconds";
      when "../load-interval = 'true'";
      //n-ext:maps-to "/ac:devices/ac:device/if:interfaces/interface/load-interval-delay";
    }
    leaf hold-queue-in {
      type boolean;
      description
        "hold-queue-in: True/False";
    }
    leaf in-queue-length {
      type uint32 {
        range "0..240000";
      }
      description
        "0..240000";
      when "../hold-queue-in = 'true'";
      //n-ext:maps-to "/ac:devices/ac:device/if:interfaces/interface/in-queue-length";
    }
    leaf hold-queue-out {
      type boolean;
      description
        "hold-queue-out: True/False";
    }
    leaf out-queue-length {
      type uint32 {
        range "0..240000";
      }
      description
        "0..240000";
      when "../hold-queue-out = 'true'";
      //n-ext:maps-to "/ac:devices/ac:device/if:interfaces/interface/out-queue-length";
    }
  }

  grouping ic-local1 {
    description
      "subnetwork properties";
    leaf cidr {
      type leafref {
        path "/ip:ipaddress-pools/ip:ipaddress-pool/ip:name";
      }
      n-ext-ui:ncx-ext-pagination "paginate";
      description
        "Select IPAM Subnet";
      //mandatory true;
    }
    leaf inbound-policy {
      type leafref {
        path "/ac:services/cpedeployment:managed-cpe-services/customer[name=current()/../../../../../name]/qos-service/policies/policy/name";
      }
      description
        "Select QoS Inbound Policy";
      when "../hierarchical-inbound-policy = 'false'";
    }
    leaf hierarchical-inbound-policy {
      type boolean;
      description
        "Check to apply ingress HQoS";
    }
    leaf hierarchical-policy {
      type leafref {
        path "/ac:services/cpedeployment:managed-cpe-services/customer[name=current()/../../../../../name]/qos-service/hierarchical-policy/policy/name";
      }
      description
        "Select Ingress HQoS policy";
      when "../hierarchical-inbound-policy = 'true'";
    }
    leaf auto-negotiation {
      type boolean;
      description
        "auto-negotiation: True/False";
      default "false";
    }
    leaf speed {
      type enumeration {
        enum "10";
        enum "100";
        enum "1000";
        enum "10000";
      }
      description
        "Speed in Mbps, Example: 10, 100, 1000, auto";
      when "../auto-negotiation = 'false'";
      //      n-ext:maps-to "/ac:devices/device/InfSpeedAndDuplex/speed";
    }
    leaf duplex {
      type enumeration {
        enum "half";
        enum "full";
        enum "auto";
      }
      description
        "Duplex options, 'auto' or 'full' or 'half' ";
      when "../auto-negotiation = 'false'";
      //      n-ext:maps-to "/ac:devices/device/InfSpeedAndDuplex/duplex";
    }
    leaf load-interval {
      type boolean;
      description
        "load-interval: True/False";
    }
    leaf load-interval-delay {
      type uint16 {
        range "30 | 60 | 90 | 120 | 150 | 180 | 210 | 240 | 270 | 300 | 330 | 360 | 390 | 420 | 450 | 480 | 510 | 540 | 570 | 600";
      }
      description
        "Range in between 30 to 600 and Load interval must be in increments of 30 seconds";
      when "../load-interval = 'true'";
      //n-ext:maps-to "/ac:devices/ac:device/if:interfaces/interface/load-interval-delay";
    }
    leaf hold-queue-in {
      type boolean;
      description
        "hold-queue-in: True/False";
    }
    leaf in-queue-length {
      type uint32 {
        range "0..240000";
      }
      description
        "0..240000";
      when "../hold-queue-in = 'true'";
    }
    leaf hold-queue-out {
      type boolean;
      description
        "hold-queue-out: True/False";
    }
    leaf out-queue-length {
      type uint32 {
        range "0..240000";
      }
      description
        "0..240000";
      when "../hold-queue-out = 'true'";
    }
  }

  grouping ic-local {
    description
      "subnetwork properties";
    leaf cidr {
      type inet:ipv4-prefix;
      description
        "cidr";
      mandatory true;
    }
    leaf inbound-policy {
      type leafref {
        path "/ac:services/cpedeployment:managed-cpe-services/customer[name=current()/../../../../../name]/qos-service/policies/policy/name";
      }
      description
        "inbound-policy";
      //n-ext:maps-to "/ac:devices/ac:device/interface:interfaces/interface/inbound-qos";
      when "../hierarchical-inbound-policy = 'false'";
    }
    leaf outbound-lan-policy {
      type leafref {
        path "/ac:services/cpedeployment:managed-cpe-services/customer[name=current()/../../../../../name]/qos-service/policies/policy/name";
      }
      description
        "Select QoS Outbound Policy";
      //n-ext:maps-to "/ac:devices/ac:device/interface:interfaces/interface/outbound-qos";
      when "../hierarchical-lan-outbound-policy = 'false'";
    }
    leaf hierarchical-inbound-policy {
      type boolean;
      description
        "hierarchical-inbound-policy: True/False";
    }
    leaf hierarchical-policy {
      type leafref {
        path "/ac:services/cpedeployment:managed-cpe-services/customer[name=current()/../../../../../name]/qos-service/hierarchical-policy/policy/name";
      }
      description
        "hierarchical-policy";
      //n-ext:maps-to "/ac:devices/ac:device/interface:interfaces/interface/inbound-qos";
      when "../hierarchical-inbound-policy = 'true'";
    }
    leaf hierarchical-lan-outbound-policy {
      type boolean;
      description
        "Check to apply egress QoS";
    }
    leaf hierarchical-egress-policy {
      type leafref {
        path "/ac:services/cpedeployment:managed-cpe-services/customer[name=current()/../../../../../name]/qos-service/hierarchical-policy/policy/name";
      }
      description
        "Select Egress HQoS Policy";
      when "../hierarchical-lan-outbound-policy = 'true'";
    }
    leaf shape-average-rate {
      type uint64 {
        range "8000..10000000000";
      }
      description
        "Enter Shape Average Rate for Outbound QoS Policy";
      //when "../hierarchical-lan-outbound-policy = 'true' ";
      //n-ext:maps-to "/ac:devices/ac:device/qos:policy-maps/policy-map[name=current()/../name]/class-entry/shape-average";
    }
    leaf police-cir-rate {
      type uint64 {
        range "8000..10000000000";
      }
      description
        "Enter Police Rate for Inbound QoS Policy";
    }
    leaf auto-negotiation {
      type boolean;
      description
        "auto-negotiation: True/False";
      default "false";
    }
    leaf speed {
      type enumeration {
        enum "10";
        enum "100";
        enum "1000";
        enum "10000";
      }
      description
        "Speed in Mbps, Example: 10, 100, 1000, auto";
      when "../auto-negotiation = 'false'";
      //      n-ext:maps-to "/ac:devices/device/InfSpeedAndDuplex/speed";
      //n-ext:maps-to "/ac:devices/ac:device/if:interfaces/interface/link-speed";
    }
    leaf duplex {
      type enumeration {
        enum "half";
        enum "full";
        enum "auto";
      }
      description
        "Duplex options, 'auto' or 'full' or 'half' ";
      when "../auto-negotiation = 'false'";
      //      n-ext:maps-to "/ac:devices/device/InfSpeedAndDuplex/duplex";
      //n-ext:maps-to "/ac:devices/ac:device/if:interfaces/interface/duplex";
    }
    leaf load-interval {
      type boolean;
      description
        "load-interval: True/False";
    }
    leaf load-interval-delay {
      type uint16 {
        range "30 | 60 | 90 | 120 | 150 | 180 | 210 | 240 | 270 | 300 | 330 | 360 | 390 | 420 | 450 | 480 | 510 | 540 | 570 | 600";
      }
      description
        "Range in between 30 to 600 and Load interval must be in increments of 30 seconds";
      when "../load-interval = 'true'";
      //n-ext:maps-to "/ac:devices/ac:device/if:interfaces/interface/load-interval-delay";
    }
    leaf hold-queue-in {
      type boolean;
      description
        "hold-queue-in: True/False";
    }
    leaf in-queue-length {
      type uint32 {
        range "0..240000";
      }
      description
        "0..240000";
      when "../hold-queue-in = 'true'";
      //n-ext:maps-to "/ac:devices/ac:device/if:interfaces/interface/in-queue-length";
    }
    leaf hold-queue-out {
      type boolean;
      description
        "hold-queue-out: True/False";
    }
    leaf out-queue-length {
      type uint32 {
        range "0..240000";
      }
      description
        "0..240000";
      when "../hold-queue-out = 'true'";
      //n-ext:maps-to "/ac:devices/ac:device/if:interfaces/interface/out-queue-length";
    }
  }

  grouping ic-local-props1 {
    description
      "subnetwork properties";
    leaf cidr {
      type leafref {
        path "/ip:ipaddress-pools/ip:ipaddress-pool/ip:name";
      }
      n-ext-ui:ncx-ext-pagination "paginate";
      description
        "cidr";
      mandatory true;
    }
    leaf auto-negotiation {
      type boolean;
      description
        "auto-negotiation: True/False";
      default "false";
    }
    leaf speed {
      type enumeration {
        enum "10";
        enum "100";
        enum "1000";
        enum "10000";
      }
      description
        "Speed in Mbps, Example: 10, 100, 1000, auto";
      when "../auto-negotiation = 'false'";
      //n-ext:maps-to "/ac:devices/ac:device/interfaces/interface/link-speed";
    }
    leaf duplex {
      type enumeration {
        enum "half";
        enum "full";
        enum "auto";
      }
      description
        "Duplex options, 'auto' or 'full' or 'half' ";
      when "../auto-negotiation = 'false'";
      //n-ext:maps-to "/ac:devices/ac:device/interfaces/interface/duplex";
    }
    leaf load-interval {
      type boolean;
      description
        "load-interval: True/False";
    }
    leaf load-interval-delay {
      type uint16 {
        range "30 | 60 | 90 | 120 | 150 | 180 | 210 | 240 | 270 | 300 | 330 | 360 | 390 | 420 | 450 | 480 | 510 | 540 | 570 | 600";
      }
      description
        "Range in between 30 to 600 and Load interval must be in increments of 30 seconds";
      when "../load-interval = 'true'";
      //n-ext:maps-to "/ac:devices/ac:device/if:interfaces/interface/load-interval-delay";
    }
    leaf hold-queue-in {
      type boolean;
      description
        "hold-queue-in: True/False";
    }
    leaf in-queue-length {
      type uint32 {
        range "0..240000";
      }
      description
        "0..240000";
      when "../hold-queue-in = 'true'";
    }
    leaf hold-queue-out {
      type boolean;
      description
        "hold-queue-out: True/False";
    }
    leaf out-queue-length {
      type uint32 {
        range "0..240000";
      }
      description
        "0..240000";
      when "../hold-queue-out = 'true'";
    }
  }

  grouping wan-interface-def {
    leaf gateway-ip {
      type inet:ip-address;
      description
        "Valid IPv4/v6 Address (A.B.C.D for e.x: 172.16.1.1 or X::Y for e.x: 2001::1)";
    }
  }

  grouping cpe-deployment-policy-def {
    uses sm:service-def {
      refine "name" {
        config false;
      }
      refine "service-sequence" {
        config false;
      }
      refine "resource-pool" {
        n-ext-ui:ncx-ext-allowed-vals "/rp:resource-pools/rp:resource-pool[rp:parent-resource-pool=current()/../../../resource-pool]/rp:name";
        mandatory true;
      }
    }
    container cpe-primary {
      uses vrf:vrouter-def {
        refine "internal-id" {
          default "cpe-primary";
          config false;
        }
        refine "name" {
          default "cpe-primary";
        }
        refine "deploy-on" {
          config false;
        }
        refine "vrf-name" {
          config false;
        }
        refine "resource-id" {
          config false;
        }
        refine "sequence-number" {
          default "1";
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "Select Device Hostname";
        mandatory true;
      }
      uses vrouter-local-def;
      leaf level {
        type uint8;
        description
          "0..255";
        default "2";
        config false;
      }
    }
    container cpe-secondary {
      uses vrf:vrouter-def {
        refine "internal-id" {
          default "cpe-secondary";
          config false;
        }
        refine "name" {
          default "cpe-secondary";
        }
        refine "vrf-name" {
          config false;
        }
        refine "deploy-on" {
          config false;
        }
        refine "resource-id" {
          config false;
        }
        refine "sequence-number" {
          default "1";
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "Select Device Hostname";
        mandatory true;
      }
      uses vrouter-local-def;
      leaf level {
        type uint8;
        description
          "0..255";
        default "2";
        config false;
      }
    }
    container cpe-primary-cpe-secondary-ic {
      uses ic:interconnect-def {
        refine "name" {
          default "cpe-primary-cpe-secondary-ic";
          config false;
        }
        refine "deploy-on" {
          config false;
        }
        refine "interconnect-name" {
          default "cpe-primary-cpe-secondary-ic";
        }
        refine "resource-id" {
          config false;
        }
        refine "sequence-number" {
          default "41";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../cpe-secondary/internal-id";
        }
        description
          "Reference to the endpoint of the interconnect";
        default "cpe-secondary";
        config false;
      }
      list ic-profile {
        key "profile-name";
        leaf profile-name {
          type string-no-space;
          description
            "Enter B2B IC Profile";
        }
        uses ic-local1 {
          refine "inbound-policy" {
            config false;
          }
          refine "hierarchical-inbound-policy" {
            config false;
          }
          refine "hierarchical-policy" {
            config false;
          }
          refine "in-queue-length" {
            n-ext:maps-to "/ac:devices/ac:device[ac:id=current()/../../../cpe-primary/device-ip]/if:interfaces/interface/in-queue-length";
            n-ext:maps-to "/ac:devices/ac:device[ac:id=current()/../../../cpe-secondary/device-ip]/if:interfaces/interface/in-queue-length";
          }
          refine "out-queue-length" {
            n-ext:maps-to "/ac:devices/ac:device[ac:id=current()/../../../cpe-primary/device-ip]/if:interfaces/interface/out-queue-length";
            n-ext:maps-to "/ac:devices/ac:device[ac:id=current()/../../../cpe-secondary/device-ip]/if:interfaces/interface/out-queue-length";
          }
        }
      }
      list end-points {
        leaf sequence-number {
          type string;
          default "42";
          description
            "sequence-number";
          config false;
        }
        key "endpoint-name";
        uses end-point-props2;
        leaf profile-name {
          type string-no-space;
          description
            "Enter Profile Name";
          mandatory true;
        }
        list eigrp {
          leaf sequence-number {
            type string;
            default "43";
            description
              "sequence-number";
            config false;
          }
          key "name";
          uses eigrp-props-end;
        }
        list bgp-peers {
          leaf sequence-number {
            type string;
            default "36";
            description
              "sequence-number";
            config false;
          }
          key "BGP-peer-name";
          uses bgp-peer-props {
            refine "next-hop-self" {
              default "true";
            }
            refine "send-community" {
              default "true";
            }
          }
        }
      }
    }
    container primary-wan {
      uses enf:external-network-def {
        refine "internal-id" {
          default "primary-wan";
          config false;
        }
        refine "sequence-number" {
          default "37";
          config false;
        }
        refine "resource-id" {
          config false;
        }
        refine "deploy-on" {
          config false;
        }
        refine "name" {
          default "primary-wan";
        }
      }
      leaf level {
        type uint8;
        description
          "0..255";
        default "1";
        config false;
      }
      leaf primary-wan-connectivity {
        type enumeration {
          enum "MPLS";
          enum "INET";
        }
        description
          "MPLS
           INET
          ";
        default "MPLS";
      }
    }
    container cpe-primary-wan {
      uses ic:interconnect-def {
        refine "name" {
          default "cpe-primary-wan";
          config false;
        }
        refine "deploy-on" {
          config false;
        }
        refine "interconnect-name" {
          default "cpe-primary-wan";
        }
        refine "resource-id" {
          config false;
        }
        refine "sequence-number" {
          default "46";
          config false;
        }
        refine "internal-id" {
          config false;
        }
        refine "type" {
          config false;
        }
      }
      leaf endpoint1 {
        n-ext:end-point;
        type leafref {
          path "../../primary-wan/internal-id";
        }
        description
          "Reference to the endpoint of the interconnect";
        default "primary-wan";
        config false;
      }
      leaf endpoint2 {
        n-ext:end-point;
        type leafref {
          path "../../cpe-primary/internal-id";
        }
        description
          "Reference to the endpoint of the interconnect";
        default "cpe-primary";
        config false;
      }
      uses ic-local-props {
        refine "inbound-policy" {
          config false;
        }
        refine "cidr" {
          mandatory false;
          config false;
        }
        //refining as per cpe-primary/ip-address
        refine "outbound-policy" {
          n-ext:maps-to "/ac:devices/ac:device[ac:id=current()/../../cpe-primary/device-ip]/qos:policy-maps/policy-map/name";
        }
        refine "policy-name" {
          n-ext:maps-to "/ac:devices/ac:device[ac:id=current()/../../cpe-primary/device-ip]/qos:policy-maps/policy-map/name";
        }
        refine "shape-average" {
          n-ext:maps-to "/ac:devices/ac:device[ac:id=current()/../../cpe-primary/device-ip]/qos:policy-maps/policy-map[name=current()/../policy-name]/class-entry/shape-average";
        }
        refine "child-qos-policy" {
          n-ext:maps-to "/ac:devices/ac:device[ac:id=current()/../../cpe-primary/device-ip]/qos:policy-maps/policy-map[name=current()/../policy-name]/class-entry/service-policy";
        }
        refine "speed" {
          n-ext:maps-to "/ac:devices/ac:device[ac:id=current()/../../cpe-primary/device-ip]/if:interfaces/interface/link-speed";
        }
        refine "duplex" {
          n-ext:maps-to "/ac:devices/ac:device[ac:id=current()/../../cpe-primary/device-ip]/if:interfaces/interface/duplex";
        }
        refine "in-queue-length" {
          n-ext:maps-to "/ac:devices/ac:device[ac:id=current()/../../cpe-primary/device-ip]/if:interfaces/interface/in-queue-length";
        }
        refine "out-queue-length" {
          n-ext:maps-to "/ac:devices/ac:device[ac:id=current()/../../cpe-primary/device-ip]/if:interfaces/interface/out-queue-length";
        }
      }
      list end-points {
        leaf sequence-number {
          type string;
          default "47";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "48";
            description
              "sequence-number";
            config false;
          }
          key "name";
          uses eigrp-props-end;
        }
        list bgp-peers {
          leaf sequence-number {
            type string;
            default "49";
            description
              "sequence-number";
            config false;
          }
          key "BGP-peer-name";
          uses bgp-peer-props;
        }
      }
    }
    container secondary-wan {
      uses enf:external-network-def {
        refine "internal-id" {
          default "secondary-wan";
          config false;
        }
        refine "sequence-number" {
          default "50";
          config false;
        }
        refine "resource-id" {
          config false;
        }
        refine "deploy-on" {
          config false;
        }
        refine "name" {
          default "secondary-wan";
        }
      }
      leaf level {
        type uint8;
        description
          "0..255";
        default "1";
        config false;
      }
      leaf secondary-wan-connectivity {
        type enumeration {
          enum "MPLS";
          enum "INET";
        }
        description
          "MPLS
           INET
          ";
        default "MPLS";
      }
    }
    container cpe-secondary-wan {
      uses ic:interconnect-def {
        refine "name" {
          default "cpe-secondary-wan";
          config false;
        }
        refine "deploy-on" {
          config false;
        }
        refine "interconnect-name" {
          default "cpe-secondary-wan";
        }
        refine "resource-id" {
          config false;
        }
        refine "sequence-number" {
          default "51";
          config false;
        }
        refine "internal-id" {
          config false;
        }
        refine "type" {
          config false;
        }
      }
      leaf endpoint1 {
        n-ext:end-point;
        type leafref {
          path "../../secondary-wan/internal-id";
        }
        description
          "Reference to the endpoint of the interconnect";
        default "secondary-wan";
        config false;
      }
      leaf endpoint2 {
        n-ext:end-point;
        type leafref {
          path "../../cpe-secondary/internal-id";
        }
        description
          "Reference to the endpoint of the interconnect";
        default "cpe-secondary";
        config false;
      }
      uses ic-local-props {
        refine "inbound-policy" {
          config false;
        }
        refine "cidr" {
          mandatory false;
          config false;
        }
        //refining as per cpe-secondary/ip-address
        refine "outbound-policy" {
          n-ext:maps-to "/ac:devices/ac:device[ac:id=current()/../../cpe-secondary/device-ip]/qos:policy-maps/policy-map/name";
        }
        refine "policy-name" {
          n-ext:maps-to "/ac:devices/ac:device[ac:id=current()/../../cpe-secondary/device-ip]/qos:policy-maps/policy-map/name";
        }
        refine "shape-average" {
          n-ext:maps-to "/ac:devices/ac:device[ac:id=current()/../../cpe-secondary/device-ip]/qos:policy-maps/policy-map[name=current()/../policy-name]/class-entry/shape-average";
        }
        refine "child-qos-policy" {
          n-ext:maps-to "/ac:devices/ac:device[ac:id=current()/../../cpe-secondary/device-ip]/qos:policy-maps/policy-map[name=current()/../policy-name]/class-entry/service-policy";
        }
        refine "speed" {
          n-ext:maps-to "/ac:devices/ac:device[ac:id=current()/../../cpe-secondary/device-ip]/if:interfaces/interface/link-speed";
        }
        refine "duplex" {
          n-ext:maps-to "/ac:devices/ac:device[ac:id=current()/../../cpe-secondary/device-ip]/if:interfaces/interface/duplex";
        }
        refine "in-queue-length" {
          n-ext:maps-to "/ac:devices/ac:device[ac:id=current()/../../cpe-secondary/device-ip]/if:interfaces/interface/in-queue-length";
        }
        refine "out-queue-length" {
          n-ext:maps-to "/ac:devices/ac:device[ac:id=current()/../../cpe-secondary/device-ip]/if:interfaces/interface/out-queue-length";
        }
      }
      list end-points {
        leaf sequence-number {
          type string;
          default "52";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "53";
            description
              "sequence-number";
            config false;
          }
          key "name";
          uses eigrp-props-end;
        }
        list bgp-peers {
          leaf sequence-number {
            type string;
            default "54";
            description
              "sequence-number";
            config false;
          }
          key "BGP-peer-name";
          uses bgp-peer-props;
        }
      }
    }
    container lan {
      uses vnf:virtual-network-def {
        refine "internal-id" {
          default "Cust-LAN";
          config false;
        }
        refine "sequence-number" {
          default "55";
          config false;
        }
        refine "resource-id" {
          config false;
        }
        refine "deploy-on" {
          config false;
        }
        refine "name" {
          default "lan";
        }
      }
      leaf level {
        type uint8;
        description
          "0..255";
        default "3";
        config false;
      }
      list switches {
        leaf sequence-number {
          type string;
          default "130";
          description
            "sequence-number";
          config false;
        }
        key "device";
        uses switch-def;
      }
    }
    container cpe-lan {
      uses ic:interconnect-def {
        refine "name" {
          default "cpe-lan";
          config false;
        }
        refine "deploy-on" {
          config false;
        }
        refine "interconnect-name" {
          default "cpe-lan";
        }
        refine "resource-id" {
          config false;
        }
        refine "sequence-number" {
          default "56";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../cpe-secondary/internal-id";
        }
        description
          "Reference to the endpoint of the interconnect";
        default "cpe-secondary";
        config false;
      }
      leaf endpoint3 {
        n-ext:end-point;
        type leafref {
          path "../../lan/internal-id";
        }
        description
          "Reference to the endpoint of the interconnect";
        default "Cust-LAN";
        config false;
      }
      uses ic-local-props {
        refine "hierarchical-outbound-policy" {
          config false;
        }
        refine "outbound-policy" {
          config false;
        }
        refine "policy-name" {
          config false;
        }
        refine "shape-average" {
          config false;
        }
        refine "child-qos-policy" {
          config false;
        }
        refine "inbound-policy" {
          config false;
        }
        refine "cidr" {
          mandatory false;
          config false;
        }
        refine "auto-negotiation" {
          config false;
        }
        refine "speed" {
          config false;
        }
        refine "duplex" {
          config false;
        }
        refine "load-interval" {
          config false;
        }
        refine "hold-queue-in" {
          config false;
        }
        refine "hold-queue-out" {
          config false;
        }
      }
      leaf hsrp-version {
        type uint8;
        description
          "0..255";
        default "2";
        config false;
      }
      leaf hsrp-standby-ip {
        type inet:ipv4-address;
        description
          "Valid IPv4 Address (A.B.C.D for e.x: 172.16.1.1)";
        config false;
        //n-ext:maps-to "/ac:devices/device/if:interfaces/interface/hsrp:hsrp/ip-address";
        //mandatory true;
      }
      leaf hsrp-group {
        type uint16 {
          range "0..4095";
        }
        description
          "0..4095";
        config false;
        //n-ext:maps-to "/ac:devices/device/if:interfaces/interface/hsrp:hsrp/group";
        //mandatory true;
      }
      leaf hsrp-preempt {
        type boolean;
        description
          "hsrp-preempt: True/False";
        config false;
        //n-ext:maps-to "/ac:devices/device/if:interfaces/interface/hsrp:hsrp/hsrp-preempt";
      }
      leaf hsrp-preempt-reload-delay {
        description
          "Enter the HSRP preempt delay in taking over active role in the range 0 to 3600 seconds";
        type uint16 {
          range "0..3600";
        }
        when "../hsrp-preempt = 'true' ";
        config false;
        //n-ext:maps-to "/ac:devices/device/if:interfaces/interface/hsrp:hsrp/preempt-reload";
      }
      leaf auth-type {
        type enumeration {
          enum "md5-key-chain";
          enum "md5-key-string";
          enum "text";
          enum "key-string";
        }
        description
          "md5-key-chain
           md5-key-string
           text
           key-string
          ";
        config false;
      }
      leaf auth-password {
        type string {
          length "1..50";
        }
        description
          "string";
        config false;
        //n-ext:maps-to "/ac:devices/device/if:interfaces/interface/hsrp:hsrp/auth-key";
      }
      leaf hsrp-timers {
        type boolean;
        description
          "hsrp-timers: True/False";
        config false;
      }
      leaf hello-interval-sec {
        type uint16 {
          range "1..254";
        }
        description
          "1..254";
        when "../hsrp-timers = 'true'";
        config false;
      }
      leaf hello-interval-msec {
        type uint16 {
          range "15..999";
        }
        description
          "15..999";
        default "250";
        when "../hsrp-timers = 'true'";
        config false;
      }
      leaf hold-time-sec {
        type uint16 {
          range "1..255";
        }
        description
          "1..255";
        default "1";
        when "../hsrp-timers = 'true'";
        config false;
      }
      leaf hold-time-msec {
        type uint16 {
          range "50..3000";
        }
        description
          "50..3000";
        when "../hsrp-timers = 'true'";
        config false;
      }
      list lan-profile {
        key "profile-name";
        leaf profile-name {
          type string-no-space;
          description
            "Enter LAN Profile Name";
        }
        uses ic-local {
          refine "cidr" {
            mandatory false;
          }
          refine "inbound-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/inbound-qos";
            n-ext:maps-to "/ac:devices/ac:device[ac:id=current()/../../../cpe-secondary/device-ip]/interface:interfaces/interface/inbound-qos";
          }
          refine "hierarchical-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/inbound-qos";
            n-ext:maps-to "/ac:devices/ac:device[ac:id=current()/../../../cpe-secondary/device-ip]/interface:interfaces/interface/inbound-qos";
          }
          refine "hierarchical-egress-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/outbound-qos";
            n-ext:maps-to "/ac:devices/ac:device[ac:id=current()/../../../cpe-secondary/device-ip]/interface:interfaces/interface/outbound-qos";
          }
          refine "outbound-lan-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/outbound-qos";
            n-ext:maps-to "/ac:devices/ac:device[ac:id=current()/../../../cpe-secondary/device-ip]/interface:interfaces/interface/outbound-qos";
          }
          refine "speed" {
            n-ext:maps-to "/ac:devices/ac:device[ac:id=current()/../../../cpe-primary/device-ip]/if:interfaces/interface/link-speed";
            n-ext:maps-to "/ac:devices/ac:device[ac:id=current()/../../../cpe-secondary/device-ip]/if:interfaces/interface/link-speed";
          }
          refine "duplex" {
            n-ext:maps-to "/ac:devices/ac:device[ac:id=current()/../../../cpe-primary/device-ip]/if:interfaces/interface/duplex";
            n-ext:maps-to "/ac:devices/ac:device[ac:id=current()/../../../cpe-secondary/device-ip]/if:interfaces/interface/duplex";
          }
          refine "in-queue-length" {
            n-ext:maps-to "/ac:devices/ac:device[ac:id=current()/../../../cpe-primary/device-ip]/if:interfaces/interface/in-queue-length";
            n-ext:maps-to "/ac:devices/ac:device[ac:id=current()/../../../cpe-secondary/device-ip]/if:interfaces/interface/in-queue-length";
          }
          refine "out-queue-length" {
            n-ext:maps-to "/ac:devices/ac:device[ac:id=current()/../../../cpe-primary/device-ip]/if:interfaces/interface/out-queue-length";
            n-ext:maps-to "/ac:devices/ac:device[ac:id=current()/../../../cpe-secondary/device-ip]/if:interfaces/interface/out-queue-length";
          }
        }
        leaf hsrp-version {
          type uint8;
          description
            "Enter HSRP Version";
          default "2";
          n-ext:maps-to "/ac:devices/ac:device[ac:id=current()/../../../cpe-primary/device-ip]/if:interfaces/interface/hsrp:hsrp[group=current()/../hsrp-group]/version";
          //n-ext:maps-to "/ac:devices/device[id=current()/../../../cpe-secondary/device-ip]/if:interfaces/interface/hsrp:hsrp[ip-address=current()/../hsrp-standby-ip]/version";
        }
        leaf hsrp-standby-ip {
          type inet:ipv4-address;
          description
            "Enter HSRP Standby IPv4 Address";
          n-ext:maps-to "/ac:devices/ac:device[ac:id=current()/../../../cpe-primary/device-ip]/if:interfaces/interface/hsrp:hsrp[group=current()/../hsrp-group]/ip-address";
          //n-ext:maps-to "/ac:devices/device[id=current()/../../../cpe-secondary/device-ip]/if:interfaces/interface/hsrp:hsrp/ip-address";
          //mandatory true;
        }
        leaf hsrp-group {
          type uint16 {
            range "0..4095";
          }
          description
            "Enter HSRP Group";
          //n-ext:maps-to "/ac:devices/device/if:interfaces/interface/hsrp:hsrp/group";
          n-ext:maps-to "/ac:devices/ac:device[ac:id=current()/../../../cpe-primary/device-ip]/if:interfaces/interface/hsrp:hsrp/group";
          //n-ext:maps-to "/ac:devices/device[id=current()/../../../cpe-secondary/device-ip]/if:interfaces/interface/hsrp:hsrp/group";
          //mandatory true;
        }
        leaf hsrp-preempt {
          type boolean;
          description
            "Check if HSRP Preempt to be enabled";
          //n-ext:maps-to "/ac:devices/device/if:interfaces/interface/hsrp:hsrp/hsrp-preempt";
          n-ext:maps-to "/ac:devices/ac:device[ac:id=current()/../../../cpe-primary/device-ip]/if:interfaces/interface/hsrp:hsrp[group=current()/../hsrp-group]/hsrp-preempt";
          //n-ext:maps-to "/ac:devices/device[id=current()/../../../cpe-secondary/device-ip]/if:interfaces/interface/hsrp:hsrp[ip-address=current()/../hsrp-standby-ip]/hsrp-preempt";
        }
        leaf hsrp-preempt-reload-delay {
          description
            "Enter the HSRP preempt delay in taking over active role in the range 0 to 3600 seconds";
          type uint16 {
            range "0..3600";
          }
          when "../hsrp-preempt = 'true' ";
          //n-ext:maps-to "/ac:devices/device/if:interfaces/interface/hsrp:hsrp/preempt-reload";
          n-ext:maps-to "/ac:devices/ac:device[ac:id=current()/../../../cpe-primary/device-ip]/if:interfaces/interface/hsrp:hsrp[group=current()/../hsrp-group]/preempt-reload";
          //n-ext:maps-to "/ac:devices/device[id=current()/../../../cpe-secondary/device-ip]/if:interfaces/interface/hsrp:hsrp[ip-address=current()/../hsrp-standby-ip]/preempt-reload";
        }
        leaf auth-type {
          type enumeration {
            enum "md5-key-chain";
            enum "md5-key-string";
            enum "text";
            enum "key-string";
          }
          description
            "md5-key-chain
             md5-key-string
             text
             key-string
            ";
          n-ext:maps-to "/ac:devices/ac:device[ac:id=current()/../../../cpe-primary/device-ip]/if:interfaces/interface/hsrp:hsrp[group=current()/../hsrp-group]/auth-type";
          //n-ext:maps-to "/ac:devices/device[id=current()/../../../cpe-secondary/device-ip]/if:interfaces/interface/hsrp:hsrp[ip-address=current()/../hsrp-standby-ip]/auth-type";
        }
        leaf auth-password {
          type string {
            length "1..50";
          }
          description
            "string";
          //n-ext:maps-to "/ac:devices/device/if:interfaces/interface/hsrp:hsrp/auth-key";
          n-ext:maps-to "/ac:devices/ac:device[ac:id=current()/../../../cpe-primary/device-ip]/if:interfaces/interface/hsrp:hsrp[group=current()/../hsrp-group]/auth-key";
          //n-ext:maps-to "/ac:devices/device[id=current()/../../../cpe-secondary/device-ip]/if:interfaces/interface/hsrp:hsrp[ip-address=current()/../hsrp-standby-ip]/auth-key";
        }
        leaf hsrp-timers {
          type boolean;
          description
            "hsrp-timers: True/False";
        }
        leaf hello-interval-sec {
          type uint16 {
            range "1..254";
          }
          description
            "1..254";
          when "../hsrp-timers = 'true'";
          n-ext:maps-to "/ac:devices/ac:device[ac:id=current()/../../../cpe-primary/device-ip]/if:interfaces/interface/hsrp:hsrp[group=current()/../hsrp-group]/timer1";
          //n-ext:maps-to "/ac:devices/device[id=current()/../../../cpe-secondary/device-ip]/if:interfaces/interface/hsrp:hsrp[ip-address=current()/../hsrp-standby-ip]/timer1";
        }
        leaf hello-interval-msec {
          type uint16 {
            range "15..999";
          }
          description
            "15..999";
          default "250";
          when "../hsrp-timers = 'true'";
          n-ext:maps-to "/ac:devices/ac:device[ac:id=current()/../../../cpe-primary/device-ip]/if:interfaces/interface/hsrp:hsrp[group=current()/../hsrp-group]/timer1";
          //n-ext:maps-to "/ac:devices/device[id=current()/../../../cpe-secondary/device-ip]/if:interfaces/interface/hsrp:hsrp[ip-address=current()/../hsrp-standby-ip]/timer1";
        }
        leaf hold-time-sec {
          type uint16 {
            range "1..255";
          }
          description
            "1..255";
          default "1";
          when "../hsrp-timers = 'true'";
          n-ext:maps-to "/ac:devices/ac:device[ac:id=current()/../../../cpe-primary/device-ip]/if:interfaces/interface/hsrp:hsrp[group=current()/../hsrp-group]/timer2";
          //n-ext:maps-to "/ac:devices/device[id=current()/../../../cpe-secondary/device-ip]/if:interfaces/interface/hsrp:hsrp[ip-address=current()/../hsrp-standby-ip]/timer2";
        }
        leaf hold-time-msec {
          type uint16 {
            range "50..3000";
          }
          description
            "50..3000";
          when "../hsrp-timers = 'true'";
          n-ext:maps-to "/ac:devices/ac:device[ac:id=current()/../../../cpe-primary/device-ip]/if:interfaces/interface/hsrp:hsrp[group=current()/../hsrp-group]/timer2";
          //n-ext:maps-to "/ac:devices/device[id=current()/../../../cpe-secondary/device-ip]/if:interfaces/interface/hsrp:hsrp[ip-address=current()/../hsrp-standby-ip]/timer2";
        }
      }
      list end-points {
        leaf sequence-number {
          type string;
          default "57";
          description
            "sequence-number";
          config false;
        }
        key "endpoint-name";
        leaf profile-name {
          type string-no-space;
          //type leafref {
          //path "/ac:services/cpedeployment:managed-cpe-services/customer[name=current()/../../../../../name]/dual-cpe-site/dual-cpe-site-services[site-name=current()/../../../site-name]/cpe-lan/lan-profile/profile-name";
          //}
          description
            "Enter Profile Name";
          //mandatory true;
        }
        uses end-point-props;
        leaf hsrp-priority {
          type uint16 {
            range "0..255";
          }
          description
            "0..255";
          //mandatory true;
          //n-ext:maps-to "/ac:devices/device[id=current()/../device-ip]/if:interfaces/interface[long-name=current()/../interface-name]/hsrp:hsrp[ip-address=current()/../../lan-profile/hsrp-standby-ip]/priority";
          n-ext:maps-to "/ac:devices/ac:device[ac:id=current()/../device-ip]/if:interfaces/interface[long-name=current()/../interface-name]/hsrp:hsrp[group=current()/../../lan-profile/hsrp-group]/priority";
        }
        leaf track {
          type uint8;
          description
            "0..255";
          n-ext:maps-to "/ac:devices/ac:device[ac:id=current()/../device-ip]/if:interfaces/interface[long-name=current()/../interface-name]/hsrp:hsrp[group=current()/../../lan-profile/hsrp-group]/track";
        }
        leaf decrement {
          type uint8;
          description
            "0..255";
          //default "120";
          n-ext:maps-to "/ac:devices/ac:device[ac:id=current()/../device-ip]/if:interfaces/interface[long-name=current()/../interface-name]/hsrp:hsrp[group=current()/../../lan-profile/hsrp-group]/decrement";
        }
        list eigrp {
          leaf sequence-number {
            type string;
            default "58";
            description
              "sequence-number";
            config false;
          }
          key "name";
          uses eigrp-props-end;
        }
        list bgp-peers {
          leaf sequence-number {
            type string;
            default "59";
            description
              "sequence-number";
            config false;
          }
          key "BGP-peer-name";
          uses bgp-peer-props;
        }
      }
    }
    uses service-validations-def;
    uses failover-fallback-dual-def;
  }

  grouping failover-fallback-dual-def {
    container failover-fallback-service {
      list failover-fallback {
        key "transaction-id";
        leaf sequence-number {
          type string;
          default "89";
          description
            "sequence-number";
          config false;
        }
        leaf transaction-id {
          type string-no-space;
          description
            "Enter Transaction Name
             This is an internal field for Anuta NCX";
        }
        leaf operation-type {
          type enumeration {
            enum "failover";
            enum "fallback";
            enum "switch-off-dps";
            enum "switch-on-dps";
          }
          mandatory true;
          description
            "Select operation type:
             - Failover: Apply policy on WAN eBGP peer(s) configured under cpe-primary-wan
             - Fallback: Restore original policy on WAN eBGP peer(s) configured under cpe-primary-wan
             - Switch-Off-DPS: Apply CoPP policy to disable OSPF adjancecy on Tunnel100
             - Switch-On-DPS:  Remove CoPP policy to re-enable OSPF adjacency on Tunnel100";
        }
        leaf failover-lan-and-b2b {
          type boolean;
          description
            "If you enable this checkbox, CoPP policy will be applied to failover any IGP/FHRP/BGP protocols running on LAN and B2B";
          when "../operation-type = 'failover'";
        }
        leaf created-by {
          type string;
          description
            "string";
          config false;
        }
        leaf created-on {
          type string;
          description
            "string";
          config false;
        }
      }
    }
  }

  grouping service-validations-def {
    container service-validations {
      leaf sequence-number {
        type string;
        default "88";
        description
          "sequence-number";
        config false;
      }
      list ping {
        description
          "ping-service";
        key "device-ip destination-ip";
        leaf device-ip {
          type leafref {
            path "/rp:resource-pools/rp:resource-pool[rp:name=current()/../../../resource-pool]/rp:device/rp:id";
          }
          description
            "device-ip";
        }
        leaf sequence-number {
          type string;
          default "89";
          description
            "sequence-number";
          config false;
        }
        leaf destination-ip {
          type inet:ip-address;
          description
            "Valid IPv4/v6 Address (A.B.C.D for e.x: 172.16.1.1 or X::Y for e.x: 2001::1)";
        }
        leaf vrf {
          type string-no-space;
          description
            "string";
        }
        leaf result {
          type enumeration {
            enum "pass";
            enum "fail";
          }
          description
            "pass
             fail
            ";
        }
      }
      list interface-status {
        description
          "interface-status";
        key "device-ip interface-name";
        leaf device-ip {
          type leafref {
            path "/rp:resource-pools/rp:resource-pool[rp:name=current()/../../../resource-pool]/rp:device/rp:id";
          }
          description
            "device-ip";
        }
        leaf sequence-number {
          type string;
          default "90";
          description
            "sequence-number";
          config false;
        }
        leaf interface-name {
          type leafref {
            path "/ac:devices/ac:device[ac:id=current()/../device-ip]/if:interfaces/if:interface/if:name";
          }
          description
            "interface-name";
        }
        leaf result {
          type string;
          description
            "string";
        }
      }
    }
  }

  grouping cpe-deployment-def {
    container dual-cpe-site {
      list dual-cpe-site-services {
        n-ext:ncx-service;
        key "site-name";
        leaf site-name {
          type string-no-space;
          description
            "Enter Site Name";
        }
        leaf bgp-as {
          type inet:as-number;
          description
            "Enter Site BGP AS Number";
          mandatory true;
          //n-ext:maps-to "/ac:devices/device/l3:vrfs/vrf/router-bgp/as-number";
          n-ext:maps-to "/ac:devices/ac:device[ac:id=current()/../cpe-primary/device-ip]/l3:vrfs/vrf[name=GLOBAL]/router-bgp/as-number";
        }
        leaf zero-touch-prov {
          type boolean;
          description
            "Check if this is a Zero Touch Provsioning Site";
        }
        leaf failover-state {
          type enumeration {
            enum "true";
            enum "false";
            enum "dps-off";
          }
          default "false";
          description
            "failover-state: True/False";
          config false;
        }
        leaf show-topology {
          type boolean;
          description
            "show-topology: True/False";
          config false;
          default "true";
        }
        leaf greenfield-site {
          type boolean;
          config false;
          description
            "greenfield-site: True/False";
        }
        leaf brownfield-site {
          type boolean;
          config false;
          description
            "brownfield-site: True/False";
        }
        leaf created-on {
          type string;
          description
            "string";
          config false;
        }
        leaf created-by {
          type string;
          description
            "string";
          config false;
        }
        uses cpe-deployment-policy-def;
        uses associated-service-def;
      }
    }
  }

  grouping cpe-tertiary-def {
    container triple-cpe-site {
      list triple-cpe-site-services {
        n-ext:ncx-service;
        key "site-name";
        leaf site-name {
          type string-no-space;
          description
            "Enter Site Name";
        }
        leaf bgp-as {
          type inet:as-number;
          description
            "Enter Site BGP AS Number";
          mandatory true;
          n-ext:maps-to "/ac:devices/ac:device[ac:id=current()/../cpe-primary/device-ip]/l3:vrfs/vrf[name=GLOBAL]/router-bgp/as-number";
        }
        leaf zero-touch-prov {
          type boolean;
          description
            "Check if this is a Zero Touch Provisioning Site";
        }
        leaf failover-state {
          type enumeration {
            enum "true";
            enum "false";
            enum "dps-off";
          }
          default "false";
          description
            "failover-state: True/False";
          config false;
        }
        leaf show-topology {
          type boolean;
          description
            "show-topology: True/False";
          config false;
          default "true";
        }
        leaf greenfield-site {
          type boolean;
          config false;
          description
            "greenfield-site: True/False";
        }
        leaf brownfield-site {
          type boolean;
          config false;
          description
            "brownfield-site: True/False";
        }
        leaf created-on {
          type string;
          description
            "string";
          config false;
        }
        leaf created-by {
          type string;
          description
            "string";
          config false;
        }
        uses cpe-tertiary-policy-def;
        uses associated-service-tertiary-def;
      }
    }
  }

  grouping associated-service-tertiary-def {
    container policy-update-services {
      n-ext:ignore-for-brownfield;
      leaf sequence-number {
        type string;
        default "75";
        description
          "sequence-number";
        config false;
      }
      leaf rtt-trigger {
        type string;
        default "false";
        description
          "naas event trap flag";
      }
      list cpe-primary-mpls {
        key "end-point";
        leaf end-point {
          type leafref {
            path "../../../cpe-primary-mpls-wan/end-points/endpoint-name";
          }
          description
            "Select Interface Name";
        }
        leaf sequence-number {
          type string;
          default "76";
          description
            "sequence-number";
          config false;
        }
        uses route-map-container-def;
      }
      list cpe-primary-inet {
        key "end-point";
        leaf end-point {
          type leafref {
            path "../../../cpe-primary-inet-wan/end-points/endpoint-name";
          }
          description
            "Select Interface Name";
        }
        leaf sequence-number {
          type string;
          default "77";
          description
            "sequence-number";
          config false;
        }
        uses route-map-container-def;
      }
      list cpe-secondary-mpls {
        key "end-point";
        leaf end-point {
          type leafref {
            path "../../../cpe-secondary-mpls-wan/end-points/endpoint-name";
          }
          description
            "Select Interface Name";
        }
        leaf sequence-number {
          type string;
          default "78";
          description
            "sequence-number";
          config false;
        }
        uses route-map-container-def;
      }
      list cpe-secondary-inet {
        key "end-point";
        leaf end-point {
          type leafref {
            path "../../../cpe-secondary-inet-wan/end-points/endpoint-name";
          }
          description
            "Select Interface Name";
        }
        leaf sequence-number {
          type string;
          default "79";
          description
            "sequence-number";
          config false;
        }
        uses route-map-container-def;
      }
      list cpe-tertiary-mpls {
        key "end-point";
        leaf end-point {
          type leafref {
            path "../../../cpe-tertiary-mpls-wan/end-points/endpoint-name";
          }
          description
            "tertiary-mpls-ic-end-point";
        }
        leaf sequence-number {
          type string;
          default "80";
          description
            "sequence-number";
          config false;
        }
        uses route-map-container-def;
      }
      list cpe-tertiary-inet {
        key "end-point";
        leaf end-point {
          type leafref {
            path "../../../cpe-tertiary-inet-wan/end-points/endpoint-name";
          }
          description
            "tertiary-inet-ic-end-point";
        }
        leaf sequence-number {
          type string;
          default "81";
          description
            "sequence-number";
          config false;
        }
        uses route-map-container-def;
      }
      container hsrp-update-service {
        n-ext:ignore-for-brownfield;
        leaf sequence-number {
          type string;
          default "82";
          description
            "sequence-number";
          config false;
        }
        leaf cpe-primary-hsrp-priority {
          type uint16 {
            range "0..255";
          }
          description
            "0..255";
        }
        leaf cpe-secondary-hsrp-priority {
          type uint16 {
            range "0..255";
          }
          description
            "0..255";
        }
        leaf cpe-tertiary-hsrp-priority {
          type uint16 {
            range "0..255";
          }
          description
            "0..255";
        }
      }
    }
  }

  grouping cpe-tertiary-policy-def {
    uses sm:service-def {
      refine "name" {
        config false;
      }
      refine "service-sequence" {
        config false;
      }
      refine "resource-pool" {
        n-ext-ui:ncx-ext-allowed-vals "/rp:resource-pools/rp:resource-pool[rp:parent-resource-pool=current()/../../../resource-pool]/rp:name";
        mandatory true;
      }
    }
    container cpe-primary {
      uses vrf:vrouter-def {
        refine "internal-id" {
          default "cpe-primary";
          config false;
        }
        refine "name" {
          default "cpe-primary";
        }
        refine "deploy-on" {
          config false;
        }
        refine "vrf-name" {
          config false;
        }
        refine "resource-id" {
          config false;
        }
        refine "sequence-number" {
          default "1";
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:routes/route[dest-ip-address=current()/../../dest-ip-address]/options[id=current()/../id]/vrf-name";
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "Select Device Hostname";
        mandatory true;
      }
      uses vrouter-local-def;
      leaf level {
        type uint8;
        description
          "0..255";
        default "2";
        config false;
      }
    }
    container cpe-secondary {
      uses vrf:vrouter-def {
        refine "internal-id" {
          default "cpe-secondary";
          config false;
        }
        refine "name" {
          default "cpe-secondary";
        }
        refine "vrf-name" {
          config false;
        }
        refine "deploy-on" {
          config false;
        }
        refine "resource-id" {
          config false;
        }
        refine "sequence-number" {
          default "1";
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:routes/route[dest-ip-address=current()/../../dest-ip-address]/options[id=current()/../id]/vrf-name";
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "Select Device Hostname";
        mandatory true;
      }
      uses vrouter-local-def;
      leaf level {
        type uint8;
        description
          "0..255";
        default "2";
        config false;
      }
    }
    container cpe-tertiary {
      uses vrf:vrouter-def {
        refine "internal-id" {
          default "cpe-tertiary";
          config false;
        }
        refine "name" {
          default "cpe-tertiary";
        }
        refine "vrf-name" {
          config false;
        }
        refine "deploy-on" {
          config false;
        }
        refine "resource-id" {
          config false;
        }
        refine "sequence-number" {
          default "1";
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:routes/route[dest-ip-address=current()/../../dest-ip-address]/options[id=current()/../id]/vrf-name";
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "Select Device Hostname";
        mandatory true;
      }
      uses vrouter-local-def;
      leaf level {
        type uint8;
        description
          "0..255";
        default "2";
        config false;
      }
    }
    container cpe-primary-cpe-secondary-ic {
      uses ic:interconnect-def {
        refine "name" {
          default "cpe-primary-cpe-secondary-ic";
          config false;
        }
        refine "deploy-on" {
          config false;
        }
        refine "interconnect-name" {
          default "cpe-primary-cpe-secondary-ic";
        }
        refine "resource-id" {
          config false;
        }
        refine "sequence-number" {
          default "41";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../cpe-secondary/internal-id";
        }
        description
          "Reference to the endpoint of the interconnect";
        default "cpe-secondary";
        config false;
      }
      list ic-profile {
        key "profile-name";
        leaf profile-name {
          type string-no-space;
          description
            "Enter B2B Interconnect Profile Name";
        }
        uses ic-local1 {
          refine "inbound-policy" {
            config false;
          }
          refine "hierarchical-inbound-policy" {
            config false;
          }
          refine "hierarchical-policy" {
            config false;
          }
        }
      }
      list end-points {
        leaf sequence-number {
          type string;
          default "42";
          description
            "sequence-number";
          config false;
        }
        key "endpoint-name";
        leaf profile-name {
          type string-no-space;
          description
            "Enter Profile Name";
          mandatory true;
        }
        uses end-point-props2;
        list eigrp {
          leaf sequence-number {
            type string;
            default "43";
            description
              "sequence-number";
            config false;
          }
          key "name";
          uses eigrp-props-end;
        }
        list bgp-peers {
          leaf sequence-number {
            type string;
            default "44";
            description
              "sequence-number";
            config false;
          }
          key "BGP-peer-name";
          uses bgp-peer-props {
            refine "next-hop-self" {
              default "true";
            }
            refine "send-community" {
              default "true";
            }
          }
        }
      }
    }
    container cpe-secondary-cpe-tertiary-ic {
      uses ic:interconnect-def {
        refine "name" {
          default "cpe-secondary-cpe-tertiary-ic";
          config false;
        }
        refine "deploy-on" {
          config false;
        }
        refine "interconnect-name" {
          default "cpe-secondary-cpe-tertiary-ic";
        }
        refine "resource-id" {
          config false;
        }
        refine "sequence-number" {
          default "45";
          config false;
        }
        refine "internal-id" {
          config false;
        }
        refine "type" {
          config false;
        }
      }
      leaf endpoint1 {
        n-ext:end-point;
        type leafref {
          path "../../cpe-secondary/internal-id";
        }
        description
          "Reference to the endpoint of the interconnect";
        default "cpe-secondary";
        config false;
      }
      leaf endpoint2 {
        n-ext:end-point;
        type leafref {
          path "../../cpe-tertiary/internal-id";
        }
        description
          "Reference to the endpoint of the interconnect";
        default "cpe-tertiary";
        config false;
      }
      list ic-profile {
        key "profile-name";
        leaf profile-name {
          type string-no-space;
          description
            "Enter B2B Interfaces Profile Name";
        }
        uses ic-local1 {
          refine "inbound-policy" {
            config false;
          }
          refine "hierarchical-inbound-policy" {
            config false;
          }
          refine "hierarchical-policy" {
            config false;
          }
        }
      }
      list end-points {
        leaf sequence-number {
          type string;
          default "46";
          description
            "sequence-number";
          config false;
        }
        key "endpoint-name";
        leaf profile-name {
          type string;
          description
            "string";
          mandatory true;
        }
        uses end-point-props2;
        list eigrp {
          leaf sequence-number {
            type string;
            default "47";
            description
              "sequence-number";
            config false;
          }
          key "name";
          uses eigrp-props-end;
        }
        list bgp-peers {
          leaf sequence-number {
            type string;
            default "48";
            description
              "sequence-number";
            config false;
          }
          key "BGP-peer-name";
          uses bgp-peer-props {
            refine "next-hop-self" {
              default "true";
            }
            refine "send-community" {
              default "true";
            }
          }
        }
      }
    }
    container cpe-tertiary-cpe-primary-ic {
      uses ic:interconnect-def {
        refine "name" {
          default "cpe-tertiary-cpe-primary-ic";
          config false;
        }
        refine "deploy-on" {
          config false;
        }
        refine "interconnect-name" {
          default "cpe-tertiary-cpe-primary-ic";
        }
        refine "resource-id" {
          config false;
        }
        refine "sequence-number" {
          default "49";
          config false;
        }
        refine "internal-id" {
          config false;
        }
        refine "type" {
          config false;
        }
      }
      leaf endpoint1 {
        n-ext:end-point;
        type leafref {
          path "../../cpe-tertiary/internal-id";
        }
        description
          "Reference to the endpoint of the interconnect";
        default "cpe-tertiary";
        config false;
      }
      leaf endpoint2 {
        n-ext:end-point;
        type leafref {
          path "../../cpe-primary/internal-id";
        }
        description
          "Reference to the endpoint of the interconnect";
        default "cpe-primary";
        config false;
      }
      list ic-profile {
        key "profile-name";
        leaf profile-name {
          type string-no-space;
          description
            "Enter B2B Interface Profile Name";
        }
        uses ic-local1 {
          refine "inbound-policy" {
            config false;
          }
          refine "hierarchical-inbound-policy" {
            config false;
          }
          refine "hierarchical-policy" {
            config false;
          }
        }
      }
      list end-points {
        leaf sequence-number {
          type string;
          default "50";
          description
            "sequence-number";
          config false;
        }
        key "endpoint-name";
        leaf profile-name {
          type string-no-space;
          description
            "Enter Profile Name";
          mandatory true;
        }
        uses end-point-props2;
        list eigrp {
          leaf sequence-number {
            type string;
            default "51";
            description
              "sequence-number";
            config false;
          }
          key "name";
          uses eigrp-props-end;
        }
        list bgp-peers {
          leaf sequence-number {
            type string;
            default "52";
            description
              "sequence-number";
            config false;
          }
          key "BGP-peer-name";
          uses bgp-peer-props {
            refine "next-hop-self" {
              default "true";
            }
            refine "send-community" {
              default "true";
            }
          }
        }
      }
    }
    container primary-mpls-wan {
      uses enf:external-network-def {
        refine "internal-id" {
          default "primary-mpls-wan";
          config false;
        }
        refine "sequence-number" {
          default "53";
          config false;
        }
        refine "resource-id" {
          config false;
        }
        refine "deploy-on" {
          config false;
        }
        refine "name" {
          default "primary-mpls-wan";
        }
      }
      leaf level {
        type uint8;
        description
          "0..255";
        default "1";
        config false;
      }
      leaf primary-mpls-wan-connectivity {
        type enumeration {
          enum "MPLS";
          enum "INET";
        }
        description
          "MPLS
           INET
          ";
        default "MPLS";
      }
    }
    container cpe-primary-mpls-wan {
      uses ic:interconnect-def {
        refine "name" {
          default "cpe-primary-mpls-wan";
          config false;
        }
        refine "deploy-on" {
          config false;
        }
        refine "interconnect-name" {
          default "cpe-primary-mpls-wan";
        }
        refine "resource-id" {
          config false;
        }
        refine "sequence-number" {
          default "54";
          config false;
        }
        refine "internal-id" {
          config false;
        }
        refine "type" {
          config false;
        }
      }
      leaf endpoint1 {
        n-ext:end-point;
        type leafref {
          path "../../primary-mpls-wan/internal-id";
        }
        description
          "Reference to the endpoint of the interconnect";
        default "primary-mpls-wan";
        config false;
      }
      leaf endpoint2 {
        n-ext:end-point;
        type leafref {
          path "../../cpe-primary/internal-id";
        }
        description
          "Reference to the endpoint of the interconnect";
        default "cpe-primary";
        config false;
      }
      uses ic-local-props {
        refine "inbound-policy" {
          config false;
        }
        refine "cidr" {
          mandatory false;
          config false;
        }
        //refining as per cpe-primary/ip-address
        refine "outbound-policy" {
          n-ext:maps-to "/ac:devices/ac:device[ac:id=current()/../../cpe-primary/device-ip]/qos:policy-maps/policy-map/name";
        }
        refine "policy-name" {
          n-ext:maps-to "/ac:devices/ac:device[ac:id=current()/../../cpe-primary/device-ip]/qos:policy-maps/policy-map/name";
        }
        refine "shape-average" {
          n-ext:maps-to "/ac:devices/ac:device[ac:id=current()/../../cpe-primary/device-ip]/qos:policy-maps/policy-map[name=current()/../policy-name]/class-entry/shape-average";
        }
        refine "child-qos-policy" {
          n-ext:maps-to "/ac:devices/ac:device[ac:id=current()/../../cpe-primary/device-ip]/qos:policy-maps/policy-map[name=current()/../policy-name]/class-entry/service-policy";
        }
        refine "speed" {
          n-ext:maps-to "/ac:devices/ac:device[ac:id=current()/../../cpe-primary/device-ip]/if:interfaces/interface/link-speed";
        }
        refine "duplex" {
          n-ext:maps-to "/ac:devices/ac:device[ac:id=current()/../../cpe-primary/device-ip]/if:interfaces/interface/duplex";
        }
        refine "in-queue-length" {
          n-ext:maps-to "/ac:devices/ac:device[ac:id=current()/../../cpe-primary/device-ip]/if:interfaces/interface/in-queue-length";
        }
        refine "out-queue-length" {
          n-ext:maps-to "/ac:devices/ac:device[ac:id=current()/../../cpe-primary/device-ip]/if:interfaces/interface/out-queue-length";
        }
      }
      list end-points {
        leaf sequence-number {
          type string;
          default "55";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Enter DMVPN Profile Name if this is an DMVPN based tunnel";
          when "../interface-type = 'Tunnel'";
          //n-ext:maps-to "/ac:devices/ac:device[ac:id=current()/../device-ip]/dmvpn:dmvpntunnels/dmvpntunnel/name";
        }
        leaf p2p {
          type boolean;
          description
            "Check if this is a Point To Point DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Mask
             This is only required for non-DMVPN Tunnel interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter Tunnel Interface Destination
             This is only required for non-DMVPN Tunnel interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Interface Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface tunnel-mss
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "56";
            description
              "sequence-number";
            config false;
          }
          key "name";
          uses eigrp-props-end;
        }
        list bgp-peers {
          leaf sequence-number {
            type string;
            default "57";
            description
              "sequence-number";
            config false;
          }
          key "BGP-peer-name";
          uses bgp-peer-props;
        }
      }
    }
    container primary-inet-wan {
      uses enf:external-network-def {
        refine "internal-id" {
          default "primary-inet-wan";
          config false;
        }
        refine "sequence-number" {
          default "58";
          config false;
        }
        refine "resource-id" {
          config false;
        }
        refine "deploy-on" {
          config false;
        }
        refine "name" {
          default "primary-inet-wan";
        }
      }
      leaf level {
        type uint8;
        description
          "0..255";
        default "1";
        config false;
      }
      leaf primary-inet-wan-connectivity {
        type enumeration {
          enum "MPLS";
          enum "INET";
        }
        description
          "MPLS
           INET
          ";
        default "INET";
      }
    }
    container cpe-primary-inet-wan {
      uses ic:interconnect-def {
        refine "name" {
          default "cpe-primary-inet-wan";
          config false;
        }
        refine "deploy-on" {
          config false;
        }
        refine "interconnect-name" {
          default "cpe-primary-inet-wan";
        }
        refine "resource-id" {
          config false;
        }
        refine "sequence-number" {
          default "59";
          config false;
        }
        refine "internal-id" {
          config false;
        }
        refine "type" {
          config false;
        }
      }
      leaf endpoint1 {
        n-ext:end-point;
        type leafref {
          path "../../primary-inet-wan/internal-id";
        }
        description
          "Reference to the endpoint of the interconnect";
        default "primary-inet-wan";
        config false;
      }
      leaf endpoint2 {
        n-ext:end-point;
        type leafref {
          path "../../cpe-primary/internal-id";
        }
        description
          "Reference to the endpoint of the interconnect";
        default "cpe-primary";
        config false;
      }
      uses ic-local-props {
        refine "inbound-policy" {
          config false;
        }
        refine "cidr" {
          mandatory false;
          config false;
        }
        //refining as per cpe-primary/ip-address
        refine "outbound-policy" {
          n-ext:maps-to "/ac:devices/ac:device[ac:id=current()/../../cpe-primary/device-ip]/qos:policy-maps/policy-map/name";
        }
        refine "policy-name" {
          n-ext:maps-to "/ac:devices/ac:device[ac:id=current()/../../cpe-primary/device-ip]/qos:policy-maps/policy-map/name";
        }
        refine "shape-average" {
          n-ext:maps-to "/ac:devices/ac:device[ac:id=current()/../../cpe-primary/device-ip]/qos:policy-maps/policy-map[name=current()/../policy-name]/class-entry/shape-average";
        }
        refine "child-qos-policy" {
          n-ext:maps-to "/ac:devices/ac:device[ac:id=current()/../../cpe-primary/device-ip]/qos:policy-maps/policy-map[name=current()/../policy-name]/class-entry/service-policy";
        }
        refine "speed" {
          n-ext:maps-to "/ac:devices/ac:device[ac:id=current()/../../cpe-primary/device-ip]/if:interfaces/interface/link-speed";
        }
        refine "duplex" {
          n-ext:maps-to "/ac:devices/ac:device[ac:id=current()/../../cpe-primary/device-ip]/if:interfaces/interface/duplex";
        }
        refine "in-queue-length" {
          n-ext:maps-to "/ac:devices/ac:device[ac:id=current()/../../cpe-primary/device-ip]/if:interfaces/interface/in-queue-length";
        }
        refine "out-queue-length" {
          n-ext:maps-to "/ac:devices/ac:device[ac:id=current()/../../cpe-primary/device-ip]/if:interfaces/interface/out-queue-length";
        }
      }
      list end-points {
        leaf sequence-number {
          type string;
          default "60";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "dmvpn-profile";
          when "../interface-type = 'Tunnel'";
          //n-ext:maps-to "/ac:devices/ac:device[ac:id=current()/../device-ip]/dmvpn:dmvpntunnels/dmvpntunnel/name";
        }
        leaf p2p {
          type boolean;
          description
            "p2p: True/False";
          when "../interface-type = 'Tunnel'";
        }
        leaf tunnel-interface-ip-address {
          type inet:ipv4-address;
          description
            "Valid IPv4 Address (A.B.C.D for e.x: 172.16.1.1)";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Valid IPv4 Mask";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Valid IPv4 Mask";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "61";
            description
              "sequence-number";
            config false;
          }
          key "name";
          uses eigrp-props-end;
        }
        list bgp-peers {
          leaf sequence-number {
            type string;
            default "62";
            description
              "sequence-number";
            config false;
          }
          key "BGP-peer-name";
          uses bgp-peer-props;
        }
      }
    }
    container secondary-mpls-wan {
      uses enf:external-network-def {
        refine "internal-id" {
          default "secondary-mpls-wan";
          config false;
        }
        refine "sequence-number" {
          default "63";
          config false;
        }
        refine "resource-id" {
          config false;
        }
        refine "deploy-on" {
          config false;
        }
        refine "name" {
          default "secondary-mpls-wan";
        }
      }
      leaf level {
        type uint8;
        description
          "0..255";
        default "1";
        config false;
      }
      leaf secondary-mpls-wan-connectivity {
        type enumeration {
          enum "MPLS";
          enum "INET";
        }
        description
          "MPLS
           INET
          ";
        default "MPLS";
      }
    }
    container cpe-secondary-mpls-wan {
      uses ic:interconnect-def {
        refine "name" {
          default "cpe-secondary-mpls-wan";
          config false;
        }
        refine "deploy-on" {
          config false;
        }
        refine "interconnect-name" {
          default "cpe-secondary-mpls-wan";
        }
        refine "resource-id" {
          config false;
        }
        refine "sequence-number" {
          default "64";
          config false;
        }
        refine "internal-id" {
          config false;
        }
        refine "type" {
          config false;
        }
      }
      leaf endpoint1 {
        n-ext:end-point;
        type leafref {
          path "../../secondary-mpls-wan/internal-id";
        }
        description
          "Reference to the endpoint of the interconnect";
        default "secondary-mpls-wan";
        config false;
      }
      leaf endpoint2 {
        n-ext:end-point;
        type leafref {
          path "../../cpe-secondary/internal-id";
        }
        description
          "Reference to the endpoint of the interconnect";
        default "cpe-secondary";
        config false;
      }
      uses ic-local-props {
        refine "inbound-policy" {
          config false;
        }
        refine "cidr" {
          mandatory false;
          config false;
        }
        //refining as per cpe-secondary/ip-address
        refine "outbound-policy" {
          n-ext:maps-to "/ac:devices/ac:device[ac:id=current()/../../cpe-secondary/device-ip]/qos:policy-maps/policy-map/name";
        }
        refine "policy-name" {
          n-ext:maps-to "/ac:devices/ac:device[ac:id=current()/../../cpe-secondary/device-ip]/qos:policy-maps/policy-map/name";
        }
        refine "shape-average" {
          n-ext:maps-to "/ac:devices/ac:device[ac:id=current()/../../cpe-secondary/device-ip]/qos:policy-maps/policy-map[name=current()/../policy-name]/class-entry/shape-average";
        }
        refine "child-qos-policy" {
          n-ext:maps-to "/ac:devices/ac:device[ac:id=current()/../../cpe-secondary/device-ip]/qos:policy-maps/policy-map[name=current()/../policy-name]/class-entry/service-policy";
        }
        refine "speed" {
          n-ext:maps-to "/ac:devices/ac:device[ac:id=current()/../../cpe-secondary/device-ip]/if:interfaces/interface/link-speed";
        }
        refine "duplex" {
          n-ext:maps-to "/ac:devices/ac:device[ac:id=current()/../../cpe-secondary/device-ip]/if:interfaces/interface/duplex";
        }
        refine "in-queue-length" {
          n-ext:maps-to "/ac:devices/ac:device[ac:id=current()/../../cpe-secondary/device-ip]/if:interfaces/interface/in-queue-length";
        }
        refine "out-queue-length" {
          n-ext:maps-to "/ac:devices/ac:device[ac:id=current()/../../cpe-secondary/device-ip]/if:interfaces/interface/out-queue-length";
        }
      }
      list end-points {
        leaf sequence-number {
          type string;
          default "65";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "66";
            description
              "sequence-number";
            config false;
          }
          key "name";
          uses eigrp-props-end;
        }
        list bgp-peers {
          leaf sequence-number {
            type string;
            default "67";
            description
              "sequence-number";
            config false;
          }
          key "BGP-peer-name";
          uses bgp-peer-props;
        }
      }
    }
    container secondary-inet-wan {
      uses enf:external-network-def {
        refine "internal-id" {
          default "secondary-inet-wan";
          config false;
        }
        refine "sequence-number" {
          default "68";
          config false;
        }
        refine "resource-id" {
          config false;
        }
        refine "deploy-on" {
          config false;
        }
        refine "name" {
          default "secondary-inet-wan";
        }
      }
      leaf level {
        type uint8;
        description
          "0..255";
        default "1";
        config false;
      }
      leaf secondary-inet-wan-connectivity {
        type enumeration {
          enum "MPLS";
          enum "INET";
        }
        description
          "MPLS
           INET
          ";
        default "INET";
      }
    }
    container cpe-secondary-inet-wan {
      uses ic:interconnect-def {
        refine "name" {
          default "cpe-secondary-inet-wan";
          config false;
        }
        refine "deploy-on" {
          config false;
        }
        refine "interconnect-name" {
          default "cpe-secondary-inet-wan";
        }
        refine "resource-id" {
          config false;
        }
        refine "sequence-number" {
          default "69";
          config false;
        }
        refine "internal-id" {
          config false;
        }
        refine "type" {
          config false;
        }
      }
      leaf endpoint1 {
        n-ext:end-point;
        type leafref {
          path "../../secondary-inet-wan/internal-id";
        }
        description
          "Reference to the endpoint of the interconnect";
        default "secondary-inet-wan";
        config false;
      }
      leaf endpoint2 {
        n-ext:end-point;
        type leafref {
          path "../../cpe-secondary/internal-id";
        }
        description
          "Reference to the endpoint of the interconnect";
        default "cpe-secondary";
        config false;
      }
      uses ic-local-props {
        refine "inbound-policy" {
          config false;
        }
        refine "cidr" {
          mandatory false;
          config false;
        }
        //refining as per cpe-secondary/ip-address
        refine "outbound-policy" {
          n-ext:maps-to "/ac:devices/ac:device[ac:id=current()/../../cpe-secondary/device-ip]/qos:policy-maps/policy-map/name";
        }
        refine "policy-name" {
          n-ext:maps-to "/ac:devices/ac:device[ac:id=current()/../../cpe-secondary/device-ip]/qos:policy-maps/policy-map/name";
        }
        refine "shape-average" {
          n-ext:maps-to "/ac:devices/ac:device[ac:id=current()/../../cpe-secondary/device-ip]/qos:policy-maps/policy-map[name=current()/../policy-name]/class-entry/shape-average";
        }
        refine "child-qos-policy" {
          n-ext:maps-to "/ac:devices/ac:device[ac:id=current()/../../cpe-secondary/device-ip]/qos:policy-maps/policy-map[name=current()/../policy-name]/class-entry/service-policy";
        }
        refine "speed" {
          n-ext:maps-to "/ac:devices/ac:device[ac:id=current()/../../cpe-secondary/device-ip]/if:interfaces/interface/link-speed";
        }
        refine "duplex" {
          n-ext:maps-to "/ac:devices/ac:device[ac:id=current()/../../cpe-secondary/device-ip]/if:interfaces/interface/duplex";
        }
        refine "in-queue-length" {
          n-ext:maps-to "/ac:devices/ac:device[ac:id=current()/../../cpe-secondary/device-ip]/if:interfaces/interface/in-queue-length";
        }
        refine "out-queue-length" {
          n-ext:maps-to "/ac:devices/ac:device[ac:id=current()/../../cpe-secondary/device-ip]/if:interfaces/interface/out-queue-length";
        }
      }
      list end-points {
        leaf sequence-number {
          type string;
          default "70";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
              If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "71";
            description
              "sequence-number";
            config false;
          }
          key "name";
          uses eigrp-props-end;
        }
        list bgp-peers {
          leaf sequence-number {
            type string;
            default "72";
            description
              "sequence-number";
            config false;
          }
          key "BGP-peer-name";
          uses bgp-peer-props;
        }
      }
    }
    container tertiary-mpls-wan {
      uses enf:external-network-def {
        refine "internal-id" {
          default "tertiary-mpls-wan";
          config false;
        }
        refine "sequence-number" {
          default "73";
          config false;
        }
        refine "resource-id" {
          config false;
        }
        refine "deploy-on" {
          config false;
        }
        refine "name" {
          default "tertiary-mpls-wan";
        }
      }
      leaf level {
        type uint8;
        description
          "0..255";
        default "1";
        config false;
      }
      leaf tertiary-mpls-wan-connectivity {
        type enumeration {
          enum "MPLS";
          enum "INET";
        }
        description
          "MPLS
           INET
          ";
        default "MPLS";
      }
    }
    container cpe-tertiary-mpls-wan {
      uses ic:interconnect-def {
        refine "name" {
          default "cpe-tertiary-mpls-wan";
          config false;
        }
        refine "deploy-on" {
          config false;
        }
        refine "interconnect-name" {
          default "cpe-tertiary-mpls-wan";
        }
        refine "resource-id" {
          config false;
        }
        refine "sequence-number" {
          default "74";
          config false;
        }
        refine "internal-id" {
          config false;
        }
        refine "type" {
          config false;
        }
      }
      leaf endpoint1 {
        n-ext:end-point;
        type leafref {
          path "../../tertiary-mpls-wan/internal-id";
        }
        description
          "Reference to the endpoint of the interconnect";
        default "tertiary-mpls-wan";
        config false;
      }
      leaf endpoint2 {
        n-ext:end-point;
        type leafref {
          path "../../cpe-tertiary/internal-id";
        }
        description
          "Reference to the endpoint of the interconnect";
        default "cpe-tertiary";
        config false;
      }
      uses ic-local-props {
        refine "inbound-policy" {
          config false;
        }
        refine "cidr" {
          mandatory false;
          config false;
        }
        //refining as per cpe-tertiary/ip-address
        refine "outbound-policy" {
          n-ext:maps-to "/ac:devices/ac:device[ac:id=current()/../../cpe-tertiary/device-ip]/qos:policy-maps/policy-map/name";
        }
        refine "policy-name" {
          n-ext:maps-to "/ac:devices/ac:device[ac:id=current()/../../cpe-tertiary/device-ip]/qos:policy-maps/policy-map/name";
        }
        refine "shape-average" {
          n-ext:maps-to "/ac:devices/ac:device[ac:id=current()/../../cpe-tertiary/device-ip]/qos:policy-maps/policy-map[name=current()/../policy-name]/class-entry/shape-average";
        }
        refine "child-qos-policy" {
          n-ext:maps-to "/ac:devices/ac:device[ac:id=current()/../../cpe-tertiary/device-ip]/qos:policy-maps/policy-map[name=current()/../policy-name]/class-entry/service-policy";
        }
        refine "speed" {
          n-ext:maps-to "/ac:devices/ac:device[ac:id=current()/../../cpe-tertiary/device-ip]/if:interfaces/interface/link-speed";
        }
        refine "duplex" {
          n-ext:maps-to "/ac:devices/ac:device[ac:id=current()/../../cpe-tertiary/device-ip]/if:interfaces/interface/duplex";
        }
        refine "in-queue-length" {
          n-ext:maps-to "/ac:devices/ac:device[ac:id=current()/../../cpe-tertiary/device-ip]/if:interfaces/interface/in-queue-length";
        }
        refine "out-queue-length" {
          n-ext:maps-to "/ac:devices/ac:device[ac:id=current()/../../cpe-tertiary/device-ip]/if:interfaces/interface/out-queue-length";
        }
      }
      list end-points {
        leaf sequence-number {
          type string;
          default "75";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Tunnel Profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Valid IPv4 Address (A.B.C.D for e.x: 172.16.1.1)";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "76";
            description
              "sequence-number";
            config false;
          }
          key "name";
          uses eigrp-props-end;
        }
        list bgp-peers {
          leaf sequence-number {
            type string;
            default "77";
            description
              "sequence-number";
            config false;
          }
          key "BGP-peer-name";
          uses bgp-peer-props;
        }
      }
    }
    container tertiary-inet-wan {
      uses enf:external-network-def {
        refine "internal-id" {
          default "tertiary-inet-wan";
          config false;
        }
        refine "sequence-number" {
          default "78";
          config false;
        }
        refine "resource-id" {
          config false;
        }
        refine "deploy-on" {
          config false;
        }
        refine "name" {
          default "tertiary-inet-wan";
        }
      }
      leaf level {
        type uint8;
        description
          "0..255";
        default "1";
        config false;
      }
      leaf tertiary-inet-wan-connectivity {
        type enumeration {
          enum "MPLS";
          enum "INET";
        }
        description
          "MPLS
           INET
          ";
        default "INET";
      }
    }
    container cpe-tertiary-inet-wan {
      uses ic:interconnect-def {
        refine "name" {
          default "cpe-tertiary-inet-wan";
          config false;
        }
        refine "deploy-on" {
          config false;
        }
        refine "interconnect-name" {
          default "cpe-tertiary-inet-wan";
        }
        refine "resource-id" {
          config false;
        }
        refine "sequence-number" {
          default "79";
          config false;
        }
        refine "internal-id" {
          config false;
        }
        refine "type" {
          config false;
        }
      }
      leaf endpoint1 {
        n-ext:end-point;
        type leafref {
          path "../../tertiary-inet-wan/internal-id";
        }
        description
          "Reference to the endpoint of the interconnect";
        default "tertiary-inet-wan";
        config false;
      }
      leaf endpoint2 {
        n-ext:end-point;
        type leafref {
          path "../../cpe-tertiary/internal-id";
        }
        description
          "Reference to the endpoint of the interconnect";
        default "cpe-tertiary";
        config false;
      }
      uses ic-local-props {
        refine "inbound-policy" {
          config false;
        }
        refine "cidr" {
          mandatory false;
          config false;
        }
        //refining as per cpe-tertiary/ip-address
        refine "outbound-policy" {
          n-ext:maps-to "/ac:devices/ac:device[ac:id=current()/../../cpe-tertiary/device-ip]/qos:policy-maps/policy-map/name";
        }
        refine "policy-name" {
          n-ext:maps-to "/ac:devices/ac:device[ac:id=current()/../../cpe-tertiary/device-ip]/qos:policy-maps/policy-map/name";
        }
        refine "shape-average" {
          n-ext:maps-to "/ac:devices/ac:device[ac:id=current()/../../cpe-tertiary/device-ip]/qos:policy-maps/policy-map[name=current()/../policy-name]/class-entry/shape-average";
        }
        refine "child-qos-policy" {
          n-ext:maps-to "/ac:devices/ac:device[ac:id=current()/../../cpe-tertiary/device-ip]/qos:policy-maps/policy-map[name=current()/../policy-name]/class-entry/service-policy";
        }
        refine "speed" {
          n-ext:maps-to "/ac:devices/ac:device[ac:id=current()/../../cpe-tertiary/device-ip]/if:interfaces/interface/link-speed";
        }
        refine "duplex" {
          n-ext:maps-to "/ac:devices/ac:device[ac:id=current()/../../cpe-tertiary/device-ip]/if:interfaces/interface/duplex";
        }
        refine "in-queue-length" {
          n-ext:maps-to "/ac:devices/ac:device[ac:id=current()/../../cpe-tertiary/device-ip]/if:interfaces/interface/in-queue-length";
        }
        refine "out-queue-length" {
          n-ext:maps-to "/ac:devices/ac:device[ac:id=current()/../../cpe-tertiary/device-ip]/if:interfaces/interface/out-queue-length";
        }
      }
      list end-points {
        leaf sequence-number {
          type string;
          default "80";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "dmvpn-profile";
          when "../interface-type = 'Tunnel'";
          //n-ext:maps-to "/ac:devices/ac:device[ac:id=current()/../device-ip]/dmvpn:dmvpntunnels/dmvpntunnel/name";
        }
        leaf p2p {
          type boolean;
          description
            "Check for P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "81";
            description
              "sequence-number";
            config false;
          }
          key "name";
          uses eigrp-props-end;
        }
        list bgp-peers {
          leaf sequence-number {
            type string;
            default "82";
            description
              "sequence-number";
            config false;
          }
          key "BGP-peer-name";
          uses bgp-peer-props;
        }
      }
    }
    container lan {
      uses vnf:virtual-network-def {
        refine "internal-id" {
          default "Cust-LAN";
          config false;
        }
        refine "sequence-number" {
          default "83";
          config false;
        }
        refine "resource-id" {
          config false;
        }
        refine "deploy-on" {
          config false;
        }
        refine "name" {
          default "lan";
        }
      }
      leaf level {
        type uint8;
        description
          "0..255";
        default "3";
        config false;
      }
      list switches {
        leaf sequence-number {
          type string;
          default "130";
          description
            "sequence-number";
          config false;
        }
        key "device";
        uses switch-def;
      }
    }
    container cpe-lan {
      uses ic:interconnect-def {
        refine "name" {
          default "cpe-lan";
          config false;
        }
        refine "deploy-on" {
          config false;
        }
        refine "interconnect-name" {
          default "cpe-lan";
        }
        refine "resource-id" {
          config false;
        }
        refine "sequence-number" {
          default "84";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../cpe-secondary/internal-id";
        }
        description
          "Reference to the endpoint of the interconnect";
        default "cpe-secondary";
        config false;
      }
      leaf endpoint3 {
        n-ext:end-point;
        type leafref {
          path "../../cpe-tertiary/internal-id";
        }
        description
          "Reference to the endpoint of the interconnect";
        default "cpe-tertiary";
        config false;
      }
      leaf endpoint4 {
        n-ext:end-point;
        type leafref {
          path "../../lan/internal-id";
        }
        description
          "Reference to the endpoint of the interconnect";
        default "Cust-LAN";
        config false;
      }
      uses ic-local-props {
        refine "hierarchical-outbound-policy" {
          config false;
        }
        refine "outbound-policy" {
          config false;
        }
        refine "policy-name" {
          config false;
        }
        refine "shape-average" {
          config false;
        }
        refine "child-qos-policy" {
          config false;
        }
        refine "inbound-policy" {
          config false;
        }
        refine "cidr" {
          mandatory false;
          config false;
        }
        refine "auto-negotiation" {
          config false;
        }
        refine "speed" {
          config false;
        }
        refine "duplex" {
          config false;
        }
        refine "load-interval" {
          config false;
        }
        refine "hold-queue-in" {
          config false;
        }
        refine "hold-queue-out" {
          config false;
        }
      }
      leaf hsrp-version {
        type uint8;
        description
          "0..255";
        default "2";
        config false;
      }
      leaf hsrp-standby-ip {
        type inet:ipv4-address;
        description
          "Valid IPv4 Address (A.B.C.D for e.x: 172.16.1.1)";
        config false;
        //n-ext:maps-to "/ac:devices/device/if:interfaces/interface/hsrp:hsrp/ip-address";
        //mandatory true;
      }
      leaf hsrp-group {
        type uint16 {
          range "0..4095";
        }
        description
          "0..4095";
        config false;
        //n-ext:maps-to "/ac:devices/device/if:interfaces/interface/hsrp:hsrp/group";
        //mandatory true;
      }
      leaf hsrp-preempt {
        type boolean;
        description
          "hsrp-preempt: True/False";
        config false;
        //n-ext:maps-to "/ac:devices/device/if:interfaces/interface/hsrp:hsrp/hsrp-preempt";
      }
      leaf hsrp-preempt-reload-delay {
        description
          "Enter the HSRP preempt delay in taking over active role in the range 0 to 3600 seconds";
        type uint16 {
          range "0..3600";
        }
        when "../hsrp-preempt = 'true' ";
        config false;
        //n-ext:maps-to "/ac:devices/device/if:interfaces/interface/hsrp:hsrp/preempt-reload";
      }
      leaf auth-type {
        type enumeration {
          enum "md5-key-chain";
          enum "md5-key-string";
          enum "text";
          enum "key-string";
        }
        description
          "md5-key-chain
           md5-key-string
           text
           key-string
          ";
        config false;
      }
      leaf auth-password {
        type string {
          length "1..50";
        }
        description
          "string";
        config false;
        //n-ext:maps-to "/ac:devices/device/if:interfaces/interface/hsrp:hsrp/auth-key";
      }
      leaf hsrp-timers {
        type boolean;
        description
          "hsrp-timers: True/False";
        config false;
      }
      leaf hello-interval-sec {
        type uint16 {
          range "1..254";
        }
        description
          "1..254";
        when "../hsrp-timers = 'true'";
        config false;
      }
      leaf hello-interval-msec {
        type uint16 {
          range "15..999";
        }
        description
          "15..999";
        default "250";
        when "../hsrp-timers = 'true'";
        config false;
      }
      leaf hold-time-sec {
        type uint16 {
          range "1..255";
        }
        description
          "1..255";
        default "1";
        when "../hsrp-timers = 'true'";
        config false;
      }
      leaf hold-time-msec {
        type uint16 {
          range "50..3000";
        }
        description
          "Enter HSRP holdtime in milliseconds";
        when "../hsrp-timers = 'true'";
        config false;
      }
      list lan-profile {
        key "profile-name";
        leaf profile-name {
          type string;
          description
            "Enter LAN Profile Name";
        }
        uses ic-local {
          refine "cidr" {
            mandatory false;
          }
          refine "inbound-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/inbound-qos";
            n-ext:maps-to "/ac:devices/ac:device[ac:id=current()/../../../cpe-secondary/device-ip]/interface:interfaces/interface/inbound-qos";
            n-ext:maps-to "/ac:devices/ac:device[ac:id=current()/../../../cpe-tertiary/device-ip]/interface:interfaces/interface/inbound-qos";
          }
          refine "hierarchical-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/inbound-qos";
            n-ext:maps-to "/ac:devices/ac:device[ac:id=current()/../../../cpe-secondary/device-ip]/interface:interfaces/interface/inbound-qos";
            n-ext:maps-to "/ac:devices/ac:device[ac:id=current()/../../../cpe-tertiary/device-ip]/interface:interfaces/interface/inbound-qos";
          }
          refine "outbound-lan-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/outbound-qos";
            n-ext:maps-to "/ac:devices/ac:device[ac:id=current()/../../../cpe-secondary/device-ip]/interface:interfaces/interface/outbound-qos";
            n-ext:maps-to "/ac:devices/ac:device[ac:id=current()/../../../cpe-tertiary/device-ip]/interface:interfaces/interface/outbound-qos";
          }
          refine "hierarchical-egress-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/outbound-qos";
            n-ext:maps-to "/ac:devices/ac:device[ac:id=current()/../../../cpe-secondary/device-ip]/interface:interfaces/interface/outbound-qos";
            n-ext:maps-to "/ac:devices/ac:device[ac:id=current()/../../../cpe-tertiary/device-ip]/interface:interfaces/interface/outbound-qos";
          }
          refine "speed" {
            n-ext:maps-to "/ac:devices/ac:device[ac:id=current()/../../../cpe-primary/device-ip]/if:interfaces/interface/link-speed";
            n-ext:maps-to "/ac:devices/ac:device[ac:id=current()/../../../cpe-secondary/device-ip]/if:interfaces/interface/link-speed";
            n-ext:maps-to "/ac:devices/ac:device[ac:id=current()/../../../cpe-tertiary/device-ip]/if:interfaces/interface/link-speed";
          }
          refine "duplex" {
            n-ext:maps-to "/ac:devices/ac:device[ac:id=current()/../../../cpe-primary/device-ip]/if:interfaces/interface/duplex";
            n-ext:maps-to "/ac:devices/ac:device[ac:id=current()/../../../cpe-secondary/device-ip]/if:interfaces/interface/duplex";
            n-ext:maps-to "/ac:devices/ac:device[ac:id=current()/../../../cpe-tertiary/device-ip]/if:interfaces/interface/duplex";
          }
          refine "in-queue-length" {
            n-ext:maps-to "/ac:devices/ac:device[ac:id=current()/../../../cpe-primary/device-ip]/if:interfaces/interface/in-queue-length";
            n-ext:maps-to "/ac:devices/ac:device[ac:id=current()/../../../cpe-secondary/device-ip]/if:interfaces/interface/in-queue-length";
            n-ext:maps-to "/ac:devices/ac:device[ac:id=current()/../../../cpe-tertiary/device-ip]/if:interfaces/interface/in-queue-length";
          }
          refine "out-queue-length" {
            n-ext:maps-to "/ac:devices/ac:device[ac:id=current()/../../../cpe-primary/device-ip]/if:interfaces/interface/out-queue-length";
            n-ext:maps-to "/ac:devices/ac:device[ac:id=current()/../../../cpe-secondary/device-ip]/if:interfaces/interface/out-queue-length";
            n-ext:maps-to "/ac:devices/ac:device[ac:id=current()/../../../cpe-tertiary/device-ip]/if:interfaces/interface/out-queue-length";
          }
        }
        leaf hsrp-version {
          type uint8;
          description
            "Enter HSRP version";
          default "2";
          n-ext:maps-to "/ac:devices/ac:device[ac:id=current()/../../../cpe-primary/device-ip]/if:interfaces/interface/hsrp:hsrp[group=current()/../hsrp-group]/version";
          //n-ext:maps-to "/ac:devices/device[id=current()/../../../cpe-secondary/device-ip]/if:interfaces/interface/hsrp:hsrp[ip-address=current()/../hsrp-standby-ip]/version";
          //n-ext:maps-to "/ac:devices/device[id=current()/../../../cpe-tertiary/device-ip]/if:interfaces/interface/hsrp:hsrp[ip-address=current()/../hsrp-standby-ip]/version";
        }
        leaf hsrp-standby-ip {
          type inet:ipv4-address;
          description
            "Enter HSRP Standby IP Address";
          n-ext:maps-to "/ac:devices/ac:device[ac:id=current()/../../../cpe-primary/device-ip]/if:interfaces/interface/hsrp:hsrp[group=current()/../hsrp-group]/ip-address";
          //n-ext:maps-to "/ac:devices/device[id=current()/../../../cpe-secondary/device-ip]/if:interfaces/interface/hsrp:hsrp/ip-address";
          //n-ext:maps-to "/ac:devices/device[id=current()/../../../cpe-tertiary/device-ip]/if:interfaces/interface/hsrp:hsrp/ip-address";
          //mandatory true;
        }
        leaf hsrp-group {
          type uint16 {
            range "0..4095";
          }
          description
            "Enter HSRP Group ID";
          //n-ext:maps-to "/ac:devices/device/if:interfaces/interface/hsrp:hsrp/group";
          n-ext:maps-to "/ac:devices/ac:device[ac:id=current()/../../../cpe-primary/device-ip]/if:interfaces/interface/hsrp:hsrp/group";
          //n-ext:maps-to "/ac:devices/device[id=current()/../../../cpe-secondary/device-ip]/if:interfaces/interface/hsrp:hsrp[ip-address=current()/../hsrp-standby-ip]/group";
          //n-ext:maps-to "/ac:devices/device[id=current()/../../../cpe-tertiary/device-ip]/if:interfaces/interface/hsrp:hsrp[ip-address=current()/../hsrp-standby-ip]/group";
          //mandatory true;
        }
        leaf hsrp-preempt {
          type boolean;
          description
            "Check to enable HSRP preemption";
          //n-ext:maps-to "/ac:devices/device/if:interfaces/interface/hsrp:hsrp/hsrp-preempt";
          n-ext:maps-to "/ac:devices/ac:device[ac:id=current()/../../../cpe-primary/device-ip]/if:interfaces/interface/hsrp:hsrp[group=current()/../hsrp-group]/hsrp-preempt";
          //n-ext:maps-to "/ac:devices/device[id=current()/../../../cpe-secondary/device-ip]/if:interfaces/interface/hsrp:hsrp[ip-address=current()/../hsrp-standby-ip]/hsrp-preempt";
          //n-ext:maps-to "/ac:devices/device[id=current()/../../../cpe-tertiary/device-ip]/if:interfaces/interface/hsrp:hsrp[ip-address=current()/../hsrp-standby-ip]/hsrp-preempt";
        }
        leaf hsrp-preempt-reload-delay {
          description
            "Enter the HSRP preempt delay in taking over active role in the range 0 to 3600 seconds";
          type uint16 {
            range "0..3600";
          }
          when "../hsrp-preempt = 'true' ";
          //n-ext:maps-to "/ac:devices/device/if:interfaces/interface/hsrp:hsrp/preempt-reload";
          n-ext:maps-to "/ac:devices/ac:device[ac:id=current()/../../../cpe-primary/device-ip]/if:interfaces/interface/hsrp:hsrp[group=current()/../hsrp-group]/preempt-reload";
          //n-ext:maps-to "/ac:devices/device[id=current()/../../../cpe-secondary/device-ip]/if:interfaces/interface/hsrp:hsrp[ip-address=current()/../hsrp-standby-ip]/preempt-reload";
          //n-ext:maps-to "/ac:devices/device[id=current()/../../../cpe-tertiary/device-ip]/if:interfaces/interface/hsrp:hsrp[ip-address=current()/../hsrp-standby-ip]/preempt-reload";
        }
        leaf auth-type {
          type enumeration {
            enum "md5-key-chain";
            enum "md5-key-string";
            enum "text";
            enum "key-string";
          }
          description
            "Enter HSRP Authentication Type";
          n-ext:maps-to "/ac:devices/ac:device[ac:id=current()/../../../cpe-primary/device-ip]/if:interfaces/interface/hsrp:hsrp[group=current()/../hsrp-group]/auth-type";
          //n-ext:maps-to "/ac:devices/device[id=current()/../../../cpe-secondary/device-ip]/if:interfaces/interface/hsrp:hsrp[ip-address=current()/../hsrp-standby-ip]/auth-type";
          //n-ext:maps-to "/ac:devices/device[id=current()/../../../cpe-tertiary/device-ip]/if:interfaces/interface/hsrp:hsrp[ip-address=current()/../hsrp-standby-ip]/auth-type";
        }
        leaf auth-password {
          type string {
            length "1..50";
          }
          description
            "Enter HSRP Authentication Password";
          //n-ext:maps-to "/ac:devices/device/if:interfaces/interface/hsrp:hsrp/auth-key";
          n-ext:maps-to "/ac:devices/ac:device[ac:id=current()/../../../cpe-primary/device-ip]/if:interfaces/interface/hsrp:hsrp[group=current()/../hsrp-group]/auth-key";
          //n-ext:maps-to "/ac:devices/device[id=current()/../../../cpe-secondary/device-ip]/if:interfaces/interface/hsrp:hsrp[ip-address=current()/../hsrp-standby-ip]/auth-key";
          //n-ext:maps-to "/ac:devices/device[id=current()/../../../cpe-tertiary/device-ip]/if:interfaces/interface/hsrp:hsrp[ip-address=current()/../hsrp-standby-ip]/auth-key";
        }
        leaf hsrp-timers {
          type boolean;
          description
            "Check to configure HSRP timers";
        }
        leaf hello-interval-sec {
          type uint16 {
            range "1..254";
          }
          description
            "Enter HSRP Hello interval in seconds";
          when "../hsrp-timers = 'true'";
          n-ext:maps-to "/ac:devices/ac:device[ac:id=current()/../../../cpe-primary/device-ip]/if:interfaces/interface/hsrp:hsrp[group=current()/../hsrp-group]/timer1";
          //n-ext:maps-to "/ac:devices/device[id=current()/../../../cpe-secondary/device-ip]/if:interfaces/interface/hsrp:hsrp[ip-address=current()/../hsrp-standby-ip]/timer1";
          //n-ext:maps-to "/ac:devices/device[id=current()/../../../cpe-tertiary/device-ip]/if:interfaces/interface/hsrp:hsrp[ip-address=current()/../hsrp-standby-ip]/timer1";
        }
        leaf hello-interval-msec {
          type uint16 {
            range "15..999";
          }
          description
            "Enter HSRP Hello interval in milliseconds";
          default "250";
          when "../hsrp-timers = 'true'";
          n-ext:maps-to "/ac:devices/ac:device[ac:id=current()/../../../cpe-primary/device-ip]/if:interfaces/interface/hsrp:hsrp[group=current()/../hsrp-group]/timer1";
          //n-ext:maps-to "/ac:devices/device[id=current()/../../../cpe-secondary/device-ip]/if:interfaces/interface/hsrp:hsrp[ip-address=current()/../hsrp-standby-ip]/timer1";
          //n-ext:maps-to "/ac:devices/device[id=current()/../../../cpe-tertiary/device-ip]/if:interfaces/interface/hsrp:hsrp[ip-address=current()/../hsrp-standby-ip]/timer1";
        }
        leaf hold-time-sec {
          type uint16 {
            range "1..255";
          }
          description
            "Enter HSRP Holdtime in seconds";
          default "1";
          when "../hsrp-timers = 'true'";
          n-ext:maps-to "/ac:devices/ac:device[ac:id=current()/../../../cpe-primary/device-ip]/if:interfaces/interface/hsrp:hsrp[group=current()/../hsrp-group]/timer2";
          //n-ext:maps-to "/ac:devices/device[id=current()/../../../cpe-secondary/device-ip]/if:interfaces/interface/hsrp:hsrp[ip-address=current()/../hsrp-standby-ip]/timer2";
          //n-ext:maps-to "/ac:devices/device[id=current()/../../../cpe-tertiary/device-ip]/if:interfaces/interface/hsrp:hsrp[ip-address=current()/../hsrp-standby-ip]/timer2";
        }
        leaf hold-time-msec {
          type uint16 {
            range "50..3000";
          }
          description
            "Enter HSRP Holdtime in milliseconds";
          when "../hsrp-timers = 'true'";
          n-ext:maps-to "/ac:devices/ac:device[ac:id=current()/../../../cpe-primary/device-ip]/if:interfaces/interface/hsrp:hsrp[group=current()/../hsrp-group]/timer2";
          //n-ext:maps-to "/ac:devices/device[id=current()/../../../cpe-secondary/device-ip]/if:interfaces/interface/hsrp:hsrp[ip-address=current()/../hsrp-standby-ip]/timer2";
          //n-ext:maps-to "/ac:devices/device[id=current()/../../../cpe-tertiary/device-ip]/if:interfaces/interface/hsrp:hsrp[ip-address=current()/../hsrp-standby-ip]/timer2";
        }
      }
      list end-points {
        leaf sequence-number {
          type string;
          default "85";
          description
            "sequence-number";
          config false;
        }
        key "endpoint-name";
        leaf profile-name {
          type string;
          description
            "Enter Profile Name";
          //mandatory true;
        }
        uses end-point-props;
        leaf hsrp-priority {
          type uint16 {
            range "0..255";
          }
          description
            "Enter HSRP Priority";
          //mandatory true;
          //n-ext:maps-to "/ac:devices/device[id=current()/../device-ip]/if:interfaces/interface[long-name=current()/../interface-name]/hsrp:hsrp[ip-address=current()/../../lan-profile/hsrp-standby-ip]/priority";
          n-ext:maps-to "/ac:devices/ac:device[ac:id=current()/../device-ip]/if:interfaces/interface[long-name=current()/../interface-name]/hsrp:hsrp[group=current()/../../lan-profile/hsrp-group]/priority";
        }
        leaf track {
          type uint8;
          description
            "Enter Track object number to be associated with HSRP group";
          n-ext:maps-to "/ac:devices/ac:device[ac:id=current()/../device-ip]/if:interfaces/interface[long-name=current()/../interface-name]/hsrp:hsrp[group=current()/../../lan-profile/hsrp-group]/track";
        }
        leaf decrement {
          type uint8;
          description
            "0..255";
          //default "120";
          n-ext:maps-to "/ac:devices/ac:device[ac:id=current()/../device-ip]/if:interfaces/interface[long-name=current()/../interface-name]/hsrp:hsrp[group=current()/../../lan-profile/hsrp-group]/decrement";
        }
        list eigrp {
          leaf sequence-number {
            type string;
            default "86";
            description
              "sequence-number";
            config false;
          }
          key "name";
          uses eigrp-props-end;
        }
        list bgp-peers {
          leaf sequence-number {
            type string;
            default "87";
            description
              "sequence-number";
            config false;
          }
          key "BGP-peer-name";
          uses bgp-peer-props;
        }
      }
    }
    uses service-validations-def;
    uses failover-fallback-triple-def;
  }

  grouping failover-fallback-triple-def {
    container failover-fallback-service {
      list failover-fallback {
        key "transaction-id";
        leaf sequence-number {
          type string;
          default "89";
          description
            "sequence-number";
          config false;
        }
        leaf transaction-id {
          type string-no-space;
          description
            "Enter Transaction Name
             This is an internal field for Anuta NCX";
        }
        leaf operation-type {
          type enumeration {
            enum "failover";
            enum "fallback";
            enum "switch-off-dps";
            enum "switch-on-dps";
          }
          mandatory true;
          description
            "Select operation type:
             - Failover: Apply policy on WAN eBGP peer(s) configured under cpe-primary-wan & cpe-secondary-wan
             - Fallback: Restore original policy on WAN eBGP peer(s) configured under cpe-primary-wan & cpe-secondary-wan
             - Switch-Off-DPS: Apply CoPP policy to disable OSPF adjancecy on Tunnel100
             - Switch-On-DPS:  Remove CoPP policy to re-enable OSPF adjacency on Tunnel100";
        }
        leaf created-by {
          type string;
          description
            "string";
          config false;
        }
        leaf created-on {
          type string;
          description
            "string";
          config false;
        }
      }
    }
  }

  grouping cpe-deployment-def-dual {
    container dual-cpe-dual-wan-site {
      list dual-cpe-dual-wan-site-services {
        n-ext:ncx-service;
        key "site-name";
        leaf site-name {
          type string-no-space;
          description
            "Enter Site Name";
        }
        leaf bgp-as {
          type inet:as-number;
          description
            "Enter BGP AS Number";
          mandatory true;
          n-ext:maps-to "/ac:devices/ac:device[ac:id=current()/../cpe-primary/device-ip]/l3:vrfs/vrf[name=GLOBAL]/router-bgp/as-number";
        }
        leaf zero-touch-prov {
          type boolean;
          description
            "Check if this is a Zero-Touch Provisioning Site";
        }
        leaf failover-state {
          type enumeration {
            enum "true";
            enum "false";
            enum "dps-off";
          }
          default "false";
          description
            "failover-state: True/False";
          config false;
        }
        leaf show-topology {
          type boolean;
          description
            "show-topology: True/False";
          config false;
          default "true";
        }
        leaf greenfield-site {
          type boolean;
          config false;
          description
            "greenfield-site: True/False";
        }
        leaf brownfield-site {
          type boolean;
          config false;
          description
            "brownfield-site: True/False";
        }
        leaf created-on {
          type string;
          description
            "string";
          config false;
        }
        leaf created-by {
          type string;
          description
            "string";
          config false;
        }
        uses cpe-deployment-policy-dual-def;
        uses associated-service-dual-wan-def;
      }
    }
  }

  grouping associated-service-dual-wan-def {
    container policy-update-services {
      n-ext:ignore-for-brownfield;
      leaf sequence-number {
        type string;
        default "63";
        description
          "sequence-number";
        config false;
      }
      leaf rtt-trigger {
        type string;
        default "false";
        description
          "naas event trap flag";
      }
      list cpe-primary-mpls {
        key "end-point";
        leaf end-point {
          type leafref {
            path "../../../cpe-primary-mpls-wan/end-points/endpoint-name";
          }
          description
            "primary-mpls-ic-end-point";
        }
        leaf sequence-number {
          type string;
          default "64";
          description
            "sequence-number";
          config false;
        }
        uses route-map-container-def;
      }
      list cpe-primary-inet {
        key "end-point";
        leaf end-point {
          type leafref {
            path "../../../cpe-primary-inet-wan/end-points/endpoint-name";
          }
          description
            "primary-inet-ic-end-point";
        }
        leaf sequence-number {
          type string;
          default "65";
          description
            "sequence-number";
          config false;
        }
        uses route-map-container-def;
      }
      list cpe-secondary-mpls {
        key "end-point";
        leaf end-point {
          type leafref {
            path "../../../cpe-secondary-mpls-wan/end-points/endpoint-name";
          }
          description
            "secondary-mpls-ic-end-point";
        }
        leaf sequence-number {
          type string;
          default "66";
          description
            "sequence-number";
          config false;
        }
        uses route-map-container-def;
      }
      list cpe-secondary-inet {
        key "end-point";
        leaf end-point {
          type leafref {
            path "../../../cpe-secondary-inet-wan/end-points/endpoint-name";
          }
          description
            "secondary-inet-ic-end-point";
        }
        leaf sequence-number {
          type string;
          default "67";
          description
            "sequence-number";
          config false;
        }
        uses route-map-container-def;
      }
      container hsrp-update-service {
        n-ext:ignore-for-brownfield;
        leaf sequence-number {
          type string;
          default "68";
          description
            "sequence-number";
          config false;
        }
        leaf cpe-primary-hsrp-priority {
          type uint16 {
            range "0..255";
          }
          description
            "0..255";
        }
        leaf cpe-secondary-hsrp-priority {
          type uint16 {
            range "0..255";
          }
          description
            "0..255";
        }
      }
    }
  }

  grouping cpe-deployment-policy-dual-def {
    uses sm:service-def {
      refine "name" {
        config false;
      }
      refine "service-sequence" {
        config false;
      }
      refine "resource-pool" {
        n-ext-ui:ncx-ext-allowed-vals "/rp:resource-pools/rp:resource-pool[rp:parent-resource-pool=current()/../../../resource-pool]/rp:name";
        mandatory true;
      }
    }
    container cpe-primary {
      uses vrf:vrouter-def {
        refine "internal-id" {
          default "cpe-primary";
          config false;
        }
        refine "name" {
          default "cpe-primary";
        }
        refine "deploy-on" {
          config false;
        }
        refine "vrf-name" {
          config false;
        }
        refine "resource-id" {
          config false;
        }
        refine "sequence-number" {
          default "1";
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:routes/route[dest-ip-address=current()/../../dest-ip-address]/options[id=current()/../id]/vrf-name";
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "device-ip";
        mandatory true;
      }
      uses vrouter-local-def;
      leaf level {
        type uint8;
        description
          "0..255";
        default "2";
        config false;
      }
    }
    container cpe-secondary {
      uses vrf:vrouter-def {
        refine "internal-id" {
          default "cpe-secondary";
          config false;
        }
        refine "name" {
          default "cpe-secondary";
        }
        refine "vrf-name" {
          config false;
        }
        refine "deploy-on" {
          config false;
        }
        refine "resource-id" {
          config false;
        }
        refine "sequence-number" {
          default "1";
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:routes/route[dest-ip-address=current()/../../dest-ip-address]/options[id=current()/../id]/vrf-name";
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "device-ip";
        mandatory true;
      }
      uses vrouter-local-def;
      leaf level {
        type uint8;
        description
          "0..255";
        default "2";
        config false;
      }
    }
    container cpe-primary-cpe-secondary-ic {
      uses ic:interconnect-def {
        refine "name" {
          default "cpe-primary-cpe-secondary-ic";
          config false;
        }
        refine "deploy-on" {
          config false;
        }
        refine "interconnect-name" {
          default "cpe-primary-cpe-secondary-ic";
        }
        refine "resource-id" {
          config false;
        }
        refine "sequence-number" {
          default "41";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../cpe-secondary/internal-id";
        }
        description
          "Reference to the endpoint of the interconnect";
        default "cpe-secondary";
        config false;
      }
      list ic-profile {
        key "profile-name";
        leaf profile-name {
          type string;
          description
            "string";
        }
        uses ic-local1 {
          refine "inbound-policy" {
            config false;
          }
          refine "hierarchical-inbound-policy" {
            config false;
          }
          refine "hierarchical-policy" {
            config false;
          }
          refine "in-queue-length" {
            n-ext:maps-to "/ac:devices/ac:device[ac:id=current()/../../../cpe-primary/device-ip]/if:interfaces/interface/in-queue-length";
            n-ext:maps-to "/ac:devices/ac:device[ac:id=current()/../../../cpe-secondary/device-ip]/if:interfaces/interface/in-queue-length";
          }
          refine "out-queue-length" {
            n-ext:maps-to "/ac:devices/ac:device[ac:id=current()/../../../cpe-primary/device-ip]/if:interfaces/interface/out-queue-length";
            n-ext:maps-to "/ac:devices/ac:device[ac:id=current()/../../../cpe-secondary/device-ip]/if:interfaces/interface/out-queue-length";
          }
        }
      }
      list end-points {
        leaf sequence-number {
          type string;
          default "42";
          description
            "sequence-number";
          config false;
        }
        key "endpoint-name";
        leaf profile-name {
          type string;
          description
            "string";
          mandatory true;
        }
        uses end-point-props2;
        list eigrp {
          leaf sequence-number {
            type string;
            default "43";
            description
              "sequence-number";
            config false;
          }
          key "name";
          uses eigrp-props-end;
        }
        list bgp-peers {
          leaf sequence-number {
            type string;
            default "44";
            description
              "sequence-number";
            config false;
          }
          key "BGP-peer-name";
          uses bgp-peer-props {
            refine "next-hop-self" {
              default "true";
            }
            refine "send-community" {
              default "true";
            }
          }
        }
      }
    }
    container primary-mpls-wan {
      uses enf:external-network-def {
        refine "internal-id" {
          default "primary-mpls-wan";
          config false;
        }
        refine "sequence-number" {
          default "45";
          config false;
        }
        refine "resource-id" {
          config false;
        }
        refine "deploy-on" {
          config false;
        }
        refine "name" {
          default "primary-mpls-wan";
        }
      }
      leaf level {
        type uint8;
        description
          "0..255";
        default "1";
        config false;
      }
      leaf primary-mpls-wan-connectivity {
        type enumeration {
          enum "MPLS";
          enum "INET";
        }
        description
          "MPLS
           INET
          ";
        default "MPLS";
      }
    }
    container cpe-primary-mpls-wan {
      uses ic:interconnect-def {
        refine "name" {
          default "cpe-primary-mpls-wan";
          config false;
        }
        refine "deploy-on" {
          config false;
        }
        refine "interconnect-name" {
          default "cpe-primary-mpls-wan";
        }
        refine "resource-id" {
          config false;
        }
        refine "sequence-number" {
          default "46";
          config false;
        }
        refine "internal-id" {
          config false;
        }
        refine "type" {
          config false;
        }
      }
      leaf endpoint1 {
        n-ext:end-point;
        type leafref {
          path "../../primary-mpls-wan/internal-id";
        }
        description
          "Reference to the endpoint of the interconnect";
        default "primary-mpls-wan";
        config false;
      }
      leaf endpoint2 {
        n-ext:end-point;
        type leafref {
          path "../../cpe-primary/internal-id";
        }
        description
          "Reference to the endpoint of the interconnect";
        default "cpe-primary";
        config false;
      }
      uses ic-local-props {
        refine "inbound-policy" {
          config false;
        }
        refine "cidr" {
          mandatory false;
          config false;
        }
        //refining as per cpe-primary/ip-address
        refine "outbound-policy" {
          n-ext:maps-to "/ac:devices/ac:device[ac:id=current()/../../cpe-primary/device-ip]/qos:policy-maps/policy-map/name";
        }
        refine "policy-name" {
          n-ext:maps-to "/ac:devices/ac:device[ac:id=current()/../../cpe-primary/device-ip]/qos:policy-maps/policy-map/name";
        }
        refine "shape-average" {
          n-ext:maps-to "/ac:devices/ac:device[ac:id=current()/../../cpe-primary/device-ip]/qos:policy-maps/policy-map[name=current()/../policy-name]/class-entry/shape-average";
        }
        refine "child-qos-policy" {
          n-ext:maps-to "/ac:devices/ac:device[ac:id=current()/../../cpe-primary/device-ip]/qos:policy-maps/policy-map[name=current()/../policy-name]/class-entry/service-policy";
        }
        refine "speed" {
          n-ext:maps-to "/ac:devices/ac:device[ac:id=current()/../../cpe-primary/device-ip]/if:interfaces/interface/link-speed";
        }
        refine "duplex" {
          n-ext:maps-to "/ac:devices/ac:device[ac:id=current()/../../cpe-primary/device-ip]/if:interfaces/interface/duplex";
        }
        refine "in-queue-length" {
          n-ext:maps-to "/ac:devices/ac:device[ac:id=current()/../../cpe-primary/device-ip]/if:interfaces/interface/in-queue-length";
        }
        refine "out-queue-length" {
          n-ext:maps-to "/ac:devices/ac:device[ac:id=current()/../../cpe-primary/device-ip]/if:interfaces/interface/out-queue-length";
        }
      }
      list end-points {
        leaf sequence-number {
          type string;
          default "47";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "dmvpn-profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "48";
            description
              "sequence-number";
            config false;
          }
          key "name";
          uses eigrp-props-end;
        }
        list bgp-peers {
          leaf sequence-number {
            type string;
            default "49";
            description
              "sequence-number";
            config false;
          }
          key "BGP-peer-name";
          uses bgp-peer-props;
        }
      }
    }
    container primary-inet-wan {
      uses enf:external-network-def {
        refine "internal-id" {
          default "primary-inet-wan";
          config false;
        }
        refine "sequence-number" {
          default "50";
          config false;
        }
        refine "resource-id" {
          config false;
        }
        refine "deploy-on" {
          config false;
        }
        refine "name" {
          default "primary-inet-wan";
        }
      }
      leaf level {
        type uint8;
        description
          "0..255";
        default "1";
        config false;
      }
      leaf primary-inet-wan-connectivity {
        type enumeration {
          enum "MPLS";
          enum "INET";
        }
        description
          "MPLS
           INET
          ";
        default "INET";
      }
    }
    container cpe-primary-inet-wan {
      uses ic:interconnect-def {
        refine "name" {
          default "cpe-primary-inet-wan";
          config false;
        }
        refine "deploy-on" {
          config false;
        }
        refine "interconnect-name" {
          default "cpe-primary-inet-wan";
        }
        refine "resource-id" {
          config false;
        }
        refine "sequence-number" {
          default "51";
          config false;
        }
        refine "internal-id" {
          config false;
        }
        refine "type" {
          config false;
        }
      }
      leaf endpoint1 {
        n-ext:end-point;
        type leafref {
          path "../../primary-inet-wan/internal-id";
        }
        description
          "Reference to the endpoint of the interconnect";
        default "primary-inet-wan";
        config false;
      }
      leaf endpoint2 {
        n-ext:end-point;
        type leafref {
          path "../../cpe-primary/internal-id";
        }
        description
          "Reference to the endpoint of the interconnect";
        default "cpe-primary";
        config false;
      }
      uses ic-local-props {
        refine "inbound-policy" {
          config false;
        }
        refine "cidr" {
          mandatory false;
          config false;
        }
        //refining as per cpe-primary/ip-address
        refine "outbound-policy" {
          n-ext:maps-to "/ac:devices/ac:device[ac:id=current()/../../cpe-primary/device-ip]/qos:policy-maps/policy-map/name";
        }
        refine "policy-name" {
          n-ext:maps-to "/ac:devices/ac:device[ac:id=current()/../../cpe-primary/device-ip]/qos:policy-maps/policy-map/name";
        }
        refine "shape-average" {
          n-ext:maps-to "/ac:devices/ac:device[ac:id=current()/../../cpe-primary/device-ip]/qos:policy-maps/policy-map[name=current()/../policy-name]/class-entry/shape-average";
        }
        refine "child-qos-policy" {
          n-ext:maps-to "/ac:devices/ac:device[ac:id=current()/../../cpe-primary/device-ip]/qos:policy-maps/policy-map[name=current()/../policy-name]/class-entry/service-policy";
        }
        refine "speed" {
          n-ext:maps-to "/ac:devices/ac:device[ac:id=current()/../../cpe-primary/device-ip]/if:interfaces/interface/link-speed";
        }
        refine "duplex" {
          n-ext:maps-to "/ac:devices/ac:device[ac:id=current()/../../cpe-primary/device-ip]/if:interfaces/interface/duplex";
        }
        refine "in-queue-length" {
          n-ext:maps-to "/ac:devices/ac:device[ac:id=current()/../../cpe-primary/device-ip]/if:interfaces/interface/in-queue-length";
        }
        refine "out-queue-length" {
          n-ext:maps-to "/ac:devices/ac:device[ac:id=current()/../../cpe-primary/device-ip]/if:interfaces/interface/out-queue-length";
        }
      }
      list end-points {
        leaf sequence-number {
          type string;
          default "52";
          description
            "sequence-number";
          config false;
        }
        key "endpoint-name";
        uses end-point-props1;
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "53";
            description
              "sequence-number";
            config false;
          }
          key "name";
          uses eigrp-props-end;
        }
        list bgp-peers {
          leaf sequence-number {
            type string;
            default "54";
            description
              "sequence-number";
            config false;
          }
          key "BGP-peer-name";
          uses bgp-peer-props;
        }
      }
    }
    container secondary-mpls-wan {
      uses enf:external-network-def {
        refine "internal-id" {
          default "secondary-mpls-wan";
          config false;
        }
        refine "sequence-number" {
          default "55";
          config false;
        }
        refine "resource-id" {
          config false;
        }
        refine "deploy-on" {
          config false;
        }
        refine "name" {
          default "secondary-mpls-wan";
        }
      }
      leaf level {
        type uint8;
        description
          "0..255";
        default "1";
        config false;
      }
      leaf secondary-mpls-wan-connectivity {
        type enumeration {
          enum "MPLS";
          enum "INET";
        }
        description
          "MPLS
           INET
          ";
        default "MPLS";
      }
    }
    container cpe-secondary-mpls-wan {
      uses ic:interconnect-def {
        refine "name" {
          default "cpe-secondary-mpls-wan";
          config false;
        }
        refine "deploy-on" {
          config false;
        }
        refine "interconnect-name" {
          default "cpe-secondary-mpls-wan";
        }
        refine "resource-id" {
          config false;
        }
        refine "sequence-number" {
          default "56";
          config false;
        }
        refine "internal-id" {
          config false;
        }
        refine "type" {
          config false;
        }
      }
      leaf endpoint1 {
        n-ext:end-point;
        type leafref {
          path "../../secondary-mpls-wan/internal-id";
        }
        description
          "Reference to the endpoint of the interconnect";
        default "secondary-mpls-wan";
        config false;
      }
      leaf endpoint2 {
        n-ext:end-point;
        type leafref {
          path "../../cpe-secondary/internal-id";
        }
        description
          "Reference to the endpoint of the interconnect";
        default "cpe-secondary";
        config false;
      }
      uses ic-local-props {
        refine "inbound-policy" {
          config false;
        }
        refine "cidr" {
          mandatory false;
          config false;
        }
        //refining as per cpe-secondary/ip-address
        refine "outbound-policy" {
          n-ext:maps-to "/ac:devices/ac:device[ac:id=current()/../../cpe-secondary/device-ip]/qos:policy-maps/policy-map/name";
        }
        refine "policy-name" {
          n-ext:maps-to "/ac:devices/ac:device[ac:id=current()/../../cpe-secondary/device-ip]/qos:policy-maps/policy-map/name";
        }
        refine "shape-average" {
          n-ext:maps-to "/ac:devices/ac:device[ac:id=current()/../../cpe-secondary/device-ip]/qos:policy-maps/policy-map[name=current()/../policy-name]/class-entry/shape-average";
        }
        refine "child-qos-policy" {
          n-ext:maps-to "/ac:devices/ac:device[ac:id=current()/../../cpe-secondary/device-ip]/qos:policy-maps/policy-map[name=current()/../policy-name]/class-entry/service-policy";
        }
        refine "speed" {
          n-ext:maps-to "/ac:devices/ac:device[ac:id=current()/../../cpe-secondary/device-ip]/if:interfaces/interface/link-speed";
        }
        refine "duplex" {
          n-ext:maps-to "/ac:devices/ac:device[ac:id=current()/../../cpe-secondary/device-ip]/if:interfaces/interface/duplex";
        }
        refine "in-queue-length" {
          n-ext:maps-to "/ac:devices/ac:device[ac:id=current()/../../cpe-secondary/device-ip]/if:interfaces/interface/in-queue-length";
        }
        refine "out-queue-length" {
          n-ext:maps-to "/ac:devices/ac:device[ac:id=current()/../../cpe-secondary/device-ip]/if:interfaces/interface/out-queue-length";
        }
      }
      list end-points {
        leaf sequence-number {
          type string;
          default "57";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "58";
            description
              "sequence-number";
            config false;
          }
          key "name";
          uses eigrp-props-end;
        }
        list bgp-peers {
          leaf sequence-number {
            type string;
            default "59";
            description
              "sequence-number";
            config false;
          }
          key "BGP-peer-name";
          uses bgp-peer-props;
        }
      }
    }
    container secondary-inet-wan {
      uses enf:external-network-def {
        refine "internal-id" {
          default "secondary-inet-wan";
          config false;
        }
        refine "sequence-number" {
          default "60";
          config false;
        }
        refine "resource-id" {
          config false;
        }
        refine "deploy-on" {
          config false;
        }
        refine "name" {
          default "secondary-inet-wan";
        }
      }
      leaf level {
        type uint8;
        description
          "0..255";
        default "1";
        config false;
      }
      leaf secondary-inet-wan-connectivity {
        type enumeration {
          enum "MPLS";
          enum "INET";
        }
        description
          "MPLS
           INET
          ";
        default "INET";
      }
    }
    container cpe-secondary-inet-wan {
      uses ic:interconnect-def {
        refine "name" {
          default "cpe-secondary-inet-wan";
          config false;
        }
        refine "deploy-on" {
          config false;
        }
        refine "interconnect-name" {
          default "cpe-secondary-inet-wan";
        }
        refine "resource-id" {
          config false;
        }
        refine "sequence-number" {
          default "61";
          config false;
        }
        refine "internal-id" {
          config false;
        }
        refine "type" {
          config false;
        }
      }
      leaf endpoint1 {
        n-ext:end-point;
        type leafref {
          path "../../secondary-inet-wan/internal-id";
        }
        description
          "Reference to the endpoint of the interconnect";
        default "secondary-inet-wan";
        config false;
      }
      leaf endpoint2 {
        n-ext:end-point;
        type leafref {
          path "../../cpe-secondary/internal-id";
        }
        description
          "Reference to the endpoint of the interconnect";
        default "cpe-secondary";
        config false;
      }
      uses ic-local-props {
        refine "inbound-policy" {
          config false;
        }
        refine "cidr" {
          mandatory false;
          config false;
        }
        //refining as per cpe-secondary/ip-address
        refine "outbound-policy" {
          n-ext:maps-to "/ac:devices/ac:device[ac:id=current()/../../cpe-secondary/device-ip]/qos:policy-maps/policy-map/name";
        }
        refine "policy-name" {
          n-ext:maps-to "/ac:devices/ac:device[ac:id=current()/../../cpe-secondary/device-ip]/qos:policy-maps/policy-map/name";
        }
        refine "shape-average" {
          n-ext:maps-to "/ac:devices/ac:device[ac:id=current()/../../cpe-secondary/device-ip]/qos:policy-maps/policy-map[name=current()/../policy-name]/class-entry/shape-average";
        }
        refine "child-qos-policy" {
          n-ext:maps-to "/ac:devices/ac:device[ac:id=current()/../../cpe-secondary/device-ip]/qos:policy-maps/policy-map[name=current()/../policy-name]/class-entry/service-policy";
        }
        refine "speed" {
          n-ext:maps-to "/ac:devices/ac:device[ac:id=current()/../../cpe-secondary/device-ip]/if:interfaces/interface/link-speed";
        }
        refine "duplex" {
          n-ext:maps-to "/ac:devices/ac:device[ac:id=current()/../../cpe-secondary/device-ip]/if:interfaces/interface/duplex";
        }
        refine "in-queue-length" {
          n-ext:maps-to "/ac:devices/ac:device[ac:id=current()/../../cpe-secondary/device-ip]/if:interfaces/interface/in-queue-length";
        }
        refine "out-queue-length" {
          n-ext:maps-to "/ac:devices/ac:device[ac:id=current()/../../cpe-secondary/device-ip]/if:interfaces/interface/out-queue-length";
        }
      }
      list end-points {
        leaf sequence-number {
          type string;
          default "62";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          when "../interface-type = 'Tunnel'";
          //n-ext:maps-to "/ac:devices/ac:device[ac:id=current()/../device-ip]/dmvpn:dmvpntunnels/dmvpntunnel/name";
        }
        leaf p2p {
          type boolean;
          description
            "Check if P2P DMVPN Tunnel";
          when "../interface-type = 'Tunnel'";
        }
        leaf tunnel-interface-ip-address {
          type inet:ipv4-address;
          description
            "Enter Tunnel Interface IP Address";
          when "../interface-type = 'Tunnel'";
          n-ext:maps-to "/ac:devices/ac:device[ac:id=current()/../device-ip]/dmvpn:dmvpntunnels/dmvpntunnel[name=current()/../tunnel-interface-id]/ipaddress";
        }
        leaf tunnel-interface-mask {
          type inet:ipv4-address;
          description
            "Enter GRE Tunnel Interface Subnet Mask
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/netmask";
        }
        leaf tunnel-interface-destination {
          type inet:ipv4-address;
          description
            "Enter GRE Tunnel Interface Destination
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tunnel-destination";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          when "../interface-type = 'Tunnel'";
          n-ext:maps-to "/ac:devices/ac:device[ac:id=current()/../device-ip]/dmvpn:dmvpntunnels/dmvpntunnel[name=current()/../tunnel-interface-id]/tunnel-source";
        }
        leaf tunnel-bandwidth {
          type uint32 {
            range "1..100000000";
          }
          description
            "Enter Tunnel Interface Bandwidth";
          units "Kbps";
          when "../interface-type = 'Tunnel'";
          n-ext:maps-to "/ac:devices/ac:device[ac:id=current()/../device-ip]/dmvpn:dmvpntunnels/dmvpntunnel[name=current()/../tunnel-interface-id]/bandwidth";
        }
        leaf tunnel-mss {
          type uint16;
          description
            "Enter GRE Tunnel Interface TCP MSS
              This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "63";
            description
              "sequence-number";
            config false;
          }
          key "name";
          uses eigrp-props-end;
        }
        list bgp-peers {
          leaf sequence-number {
            type string;
            default "52";
            description
              "sequence-number";
            config false;
          }
          key "BGP-peer-name";
          uses bgp-peer-props;
        }
      }
    }
    container lan {
      uses vnf:virtual-network-def {
        refine "internal-id" {
          default "Cust-LAN";
          config false;
        }
        refine "sequence-number" {
          default "65";
          config false;
        }
        refine "resource-id" {
          config false;
        }
        refine "deploy-on" {
          config false;
        }
        refine "name" {
          default "lan";
        }
      }
      leaf level {
        type uint8;
        description
          "0..255";
        default "3";
        config false;
      }
      list switches {
        leaf sequence-number {
          type string;
          default "130";
          description
            "sequence-number";
          config false;
        }
        key "device";
        uses switch-def;
      }
    }
    container cpe-lan {
      uses ic:interconnect-def {
        refine "name" {
          default "cpe-lan";
          config false;
        }
        refine "deploy-on" {
          config false;
        }
        refine "interconnect-name" {
          default "cpe-lan";
        }
        refine "resource-id" {
          config false;
        }
        refine "sequence-number" {
          default "66";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../cpe-secondary/internal-id";
        }
        description
          "Reference to the endpoint of the interconnect";
        default "cpe-secondary";
        config false;
      }
      leaf endpoint3 {
        n-ext:end-point;
        type leafref {
          path "../../lan/internal-id";
        }
        description
          "Reference to the endpoint of the interconnect";
        default "Cust-LAN";
        config false;
      }
      uses ic-local-props {
        refine "hierarchical-outbound-policy" {
          config false;
        }
        refine "outbound-policy" {
          config false;
        }
        refine "policy-name" {
          config false;
        }
        refine "shape-average" {
          config false;
        }
        refine "child-qos-policy" {
          config false;
        }
        refine "inbound-policy" {
          config false;
        }
        refine "cidr" {
          mandatory false;
          config false;
        }
        refine "auto-negotiation" {
          config false;
        }
        refine "speed" {
          config false;
        }
        refine "duplex" {
          config false;
        }
        refine "load-interval" {
          config false;
        }
        refine "hold-queue-in" {
          config false;
        }
        refine "hold-queue-out" {
          config false;
        }
      }
      leaf hsrp-version {
        type uint8;
        description
          "0..255";
        default "2";
        config false;
      }
      leaf hsrp-standby-ip {
        type inet:ipv4-address;
        description
          "Valid IPv4 Address (A.B.C.D for e.x: 172.16.1.1)";
        config false;
        //n-ext:maps-to "/ac:devices/device/if:interfaces/interface/hsrp:hsrp/ip-address";
        //mandatory true;
      }
      leaf hsrp-group {
        type uint16 {
          range "0..4095";
        }
        description
          "0..4095";
        config false;
        //n-ext:maps-to "/ac:devices/device/if:interfaces/interface/hsrp:hsrp/group";
        //mandatory true;
      }
      leaf hsrp-preempt {
        type boolean;
        description
          "hsrp-preempt: True/False";
        config false;
        //n-ext:maps-to "/ac:devices/device/if:interfaces/interface/hsrp:hsrp/hsrp-preempt";
      }
      leaf hsrp-preempt-reload-delay {
        description
          "Enter the HSRP preempt delay in taking over active role in the range 0 to 3600 seconds";
        type uint16 {
          range "0..3600";
        }
        when "../hsrp-preempt = 'true' ";
        config false;
        //n-ext:maps-to "/ac:devices/device/if:interfaces/interface/hsrp:hsrp/preempt-reload";
      }
      leaf auth-type {
        type enumeration {
          enum "md5-key-chain";
          enum "md5-key-string";
          enum "text";
          enum "key-string";
        }
        description
          "md5-key-chain
           md5-key-string
           text
           key-string
          ";
        config false;
      }
      leaf auth-password {
        type string {
          length "1..50";
        }
        description
          "string";
        config false;
        //n-ext:maps-to "/ac:devices/device/if:interfaces/interface/hsrp:hsrp/auth-key";
      }
      leaf hsrp-timers {
        type boolean;
        description
          "hsrp-timers: True/False";
        config false;
      }
      leaf hello-interval-sec {
        type uint16 {
          range "1..254";
        }
        description
          "1..254";
        when "../hsrp-timers = 'true'";
        config false;
      }
      leaf hello-interval-msec {
        type uint16 {
          range "15..999";
        }
        description
          "15..999";
        default "250";
        when "../hsrp-timers = 'true'";
        config false;
      }
      leaf hold-time-sec {
        type uint16 {
          range "1..255";
        }
        description
          "1..255";
        default "1";
        when "../hsrp-timers = 'true'";
        config false;
      }
      leaf hold-time-msec {
        type uint16 {
          range "50..3000";
        }
        description
          "50..3000";
        when "../hsrp-timers = 'true'";
        config false;
      }
      list lan-profile {
        key "profile-name";
        leaf profile-name {
          type string;
          description
            "string";
        }
        uses ic-local {
          refine "cidr" {
            mandatory false;
          }
          refine "inbound-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/inbound-qos";
            n-ext:maps-to "/ac:devices/ac:device[ac:id=current()/../../../cpe-secondary/device-ip]/interface:interfaces/interface/inbound-qos";
          }
          refine "hierarchical-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/inbound-qos";
            n-ext:maps-to "/ac:devices/ac:device[ac:id=current()/../../../cpe-secondary/device-ip]/interface:interfaces/interface/inbound-qos";
          }
          refine "outbound-lan-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/outbound-qos";
            n-ext:maps-to "/ac:devices/ac:device[ac:id=current()/../../../cpe-secondary/device-ip]/interface:interfaces/interface/outbound-qos";
          }
          refine "hierarchical-egress-policy" {
            //n-ext:maps-to "/ac:devices/ac:device[ac:id=current()/../../cpe/device-ip]/qos:policy-maps/policy-map/name";
            n-ext:maps-to "/ac:devices/ac:device[ac:id=current()/../../../cpe-primary/device-ip]/interface:interfaces/interface/outbound-qos";
            n-ext:maps-to "/ac:devices/ac:device[ac:id=current()/../../../cpe-secondary/device-ip]/interface:interfaces/interface/outbound-qos";
          }
          refine "speed" {
            n-ext:maps-to "/ac:devices/ac:device[ac:id=current()/../../../cpe-primary/device-ip]/if:interfaces/interface/link-speed";
            n-ext:maps-to "/ac:devices/ac:device[ac:id=current()/../../../cpe-secondary/device-ip]/if:interfaces/interface/link-speed";
          }
          refine "duplex" {
            n-ext:maps-to "/ac:devices/ac:device[ac:id=current()/../../../cpe-primary/device-ip]/if:interfaces/interface/duplex";
            n-ext:maps-to "/ac:devices/ac:device[ac:id=current()/../../../cpe-secondary/device-ip]/if:interfaces/interface/duplex";
          }
          refine "in-queue-length" {
            n-ext:maps-to "/ac:devices/ac:device[ac:id=current()/../../../cpe-primary/device-ip]/if:interfaces/interface/in-queue-length";
            n-ext:maps-to "/ac:devices/ac:device[ac:id=current()/../../../cpe-secondary/device-ip]/if:interfaces/interface/in-queue-length";
          }
          refine "out-queue-length" {
            n-ext:maps-to "/ac:devices/ac:device[ac:id=current()/../../../cpe-primary/device-ip]/if:interfaces/interface/out-queue-length";
            n-ext:maps-to "/ac:devices/ac:device[ac:id=current()/../../../cpe-secondary/device-ip]/if:interfaces/interface/out-queue-length";
          }
        }
        leaf hsrp-version {
          type uint8;
          description
            "0..255";
          default "2";
          n-ext:maps-to "/ac:devices/ac:device[ac:id=current()/../../../cpe-primary/device-ip]/if:interfaces/interface/hsrp:hsrp[group=current()/../hsrp-group]/version";
          //n-ext:maps-to "/ac:devices/device[id=current()/../../../cpe-secondary/device-ip]/if:interfaces/interface/hsrp:hsrp[ip-address=current()/../hsrp-standby-ip]/version";
        }
        leaf hsrp-standby-ip {
          type inet:ipv4-address;
          description
            "Valid IPv4 Address (A.B.C.D for e.x: 172.16.1.1)";
          n-ext:maps-to "/ac:devices/ac:device[ac:id=current()/../../../cpe-primary/device-ip]/if:interfaces/interface/hsrp:hsrp[group=current()/../hsrp-group]/ip-address";
          //n-ext:maps-to "/ac:devices/device[id=current()/../../../cpe-secondary/device-ip]/if:interfaces/interface/hsrp:hsrp/ip-address";
          //mandatory true;
        }
        leaf hsrp-group {
          type uint16 {
            range "0..4095";
          }
          description
            "0..4095";
          //n-ext:maps-to "/ac:devices/device/if:interfaces/interface/hsrp:hsrp/group";
          n-ext:maps-to "/ac:devices/ac:device[ac:id=current()/../../../cpe-primary/device-ip]/if:interfaces/interface/hsrp:hsrp/group";
          //n-ext:maps-to "/ac:devices/device[id=current()/../../../cpe-secondary/device-ip]/if:interfaces/interface/hsrp:hsrp[ip-address=current()/../hsrp-standby-ip]/group";
          //mandatory true;
        }
        leaf hsrp-preempt {
          type boolean;
          description
            "hsrp-preempt: True/False";
          //n-ext:maps-to "/ac:devices/device/if:interfaces/interface/hsrp:hsrp/hsrp-preempt";
          n-ext:maps-to "/ac:devices/ac:device[ac:id=current()/../../../cpe-primary/device-ip]/if:interfaces/interface/hsrp:hsrp[group=current()/../hsrp-group]/hsrp-preempt";
          //n-ext:maps-to "/ac:devices/device[id=current()/../../../cpe-secondary/device-ip]/if:interfaces/interface/hsrp:hsrp[ip-address=current()/../hsrp-standby-ip]/hsrp-preempt";
        }
        leaf hsrp-preempt-reload-delay {
          description
            "Enter the HSRP preempt delay in taking over active role in the range 0 to 3600 seconds";
          type uint16 {
            range "0..3600";
          }
          when "../hsrp-preempt = 'true' ";
          //n-ext:maps-to "/ac:devices/device/if:interfaces/interface/hsrp:hsrp/preempt-reload";
          n-ext:maps-to "/ac:devices/ac:device[ac:id=current()/../../../cpe-primary/device-ip]/if:interfaces/interface/hsrp:hsrp[group=current()/../hsrp-group]/preempt-reload";
          //n-ext:maps-to "/ac:devices/device[id=current()/../../../cpe-secondary/device-ip]/if:interfaces/interface/hsrp:hsrp[ip-address=current()/../hsrp-standby-ip]/preempt-reload";
        }
        leaf auth-type {
          type enumeration {
            enum "md5-key-chain";
            enum "md5-key-string";
            enum "text";
            enum "key-string";
          }
          description
            "md5-key-chain
             md5-key-string
             text
             key-string
            ";
          n-ext:maps-to "/ac:devices/ac:device[ac:id=current()/../../../cpe-primary/device-ip]/if:interfaces/interface/hsrp:hsrp[group=current()/../hsrp-group]/auth-type";
          //n-ext:maps-to "/ac:devices/device[id=current()/../../../cpe-secondary/device-ip]/if:interfaces/interface/hsrp:hsrp[ip-address=current()/../hsrp-standby-ip]/auth-type";
        }
        leaf auth-password {
          type string {
            length "1..50";
          }
          description
            "string";
          //n-ext:maps-to "/ac:devices/device/if:interfaces/interface/hsrp:hsrp/auth-key";
          n-ext:maps-to "/ac:devices/ac:device[ac:id=current()/../../../cpe-primary/device-ip]/if:interfaces/interface/hsrp:hsrp[group=current()/../hsrp-group]/auth-key";
          //n-ext:maps-to "/ac:devices/device[id=current()/../../../cpe-secondary/device-ip]/if:interfaces/interface/hsrp:hsrp[ip-address=current()/../hsrp-standby-ip]/auth-key";
        }
        leaf hsrp-timers {
          type boolean;
          description
            "hsrp-timers: True/False";
        }
        leaf hello-interval-sec {
          type uint16 {
            range "1..254";
          }
          description
            "1..254";
          when "../hsrp-timers = 'true'";
          n-ext:maps-to "/ac:devices/ac:device[ac:id=current()/../../../cpe-primary/device-ip]/if:interfaces/interface/hsrp:hsrp[group=current()/../hsrp-group]/timer1";
          //n-ext:maps-to "/ac:devices/device[id=current()/../../../cpe-secondary/device-ip]/if:interfaces/interface/hsrp:hsrp[ip-address=current()/../hsrp-standby-ip]/timer1";
        }
        leaf hello-interval-msec {
          type uint16 {
            range "15..999";
          }
          description
            "15..999";
          default "250";
          when "../hsrp-timers = 'true'";
          n-ext:maps-to "/ac:devices/ac:device[ac:id=current()/../../../cpe-primary/device-ip]/if:interfaces/interface/hsrp:hsrp[group=current()/../hsrp-group]/timer1";
          //n-ext:maps-to "/ac:devices/device[id=current()/../../../cpe-secondary/device-ip]/if:interfaces/interface/hsrp:hsrp[ip-address=current()/../hsrp-standby-ip]/timer1";
        }
        leaf hold-time-sec {
          type uint16 {
            range "1..255";
          }
          description
            "1..255";
          default "1";
          when "../hsrp-timers = 'true'";
          n-ext:maps-to "/ac:devices/ac:device[ac:id=current()/../../../cpe-primary/device-ip]/if:interfaces/interface/hsrp:hsrp[group=current()/../hsrp-group]/timer2";
          //n-ext:maps-to "/ac:devices/device[id=current()/../../../cpe-secondary/device-ip]/if:interfaces/interface/hsrp:hsrp[ip-address=current()/../hsrp-standby-ip]/timer2";
        }
        leaf hold-time-msec {
          type uint16 {
            range "50..3000";
          }
          description
            "50..3000";
          when "../hsrp-timers = 'true'";
          n-ext:maps-to "/ac:devices/ac:device[ac:id=current()/../../../cpe-primary/device-ip]/if:interfaces/interface/hsrp:hsrp[group=current()/../hsrp-group]/timer2";
          //n-ext:maps-to "/ac:devices/device[id=current()/../../../cpe-secondary/device-ip]/if:interfaces/interface/hsrp:hsrp[ip-address=current()/../hsrp-standby-ip]/timer2";
        }
      }
      list end-points {
        leaf sequence-number {
          type string;
          default "67";
          description
            "sequence-number";
          config false;
        }
        key "endpoint-name";
        leaf profile-name {
          type string;
          description
            "string";
          //mandatory true;
        }
        uses end-point-props;
        leaf hsrp-priority {
          type uint16 {
            range "0..255";
          }
          description
            "0..255";
          //mandatory true;
          //n-ext:maps-to "/ac:devices/device[id=current()/../device-ip]/if:interfaces/interface[long-name=current()/../interface-name]/hsrp:hsrp[ip-address=current()/../../lan-profile/hsrp-standby-ip]/priority";
          n-ext:maps-to "/ac:devices/ac:device[ac:id=current()/../device-ip]/if:interfaces/interface[long-name=current()/../interface-name]/hsrp:hsrp[group=current()/../../lan-profile/hsrp-group]/priority";
        }
        leaf track {
          type uint8;
          description
            "0..255";
          n-ext:maps-to "/ac:devices/ac:device[ac:id=current()/../device-ip]/if:interfaces/interface[long-name=current()/../interface-name]/hsrp:hsrp[group=current()/../../lan-profile/hsrp-group]/track";
        }
        leaf decrement {
          type uint8;
          description
            "0..255";
          //default "120";
          n-ext:maps-to "/ac:devices/ac:device[ac:id=current()/../device-ip]/if:interfaces/interface[long-name=current()/../interface-name]/hsrp:hsrp[group=current()/../../lan-profile/hsrp-group]/decrement";
        }
        list eigrp {
          leaf sequence-number {
            type string;
            default "68";
            description
              "sequence-number";
            config false;
          }
          key "name";
          uses eigrp-props-end;
        }
        list bgp-peers {
          leaf sequence-number {
            type string;
            default "69";
            description
              "sequence-number";
            config false;
          }
          key "BGP-peer-name";
          uses bgp-peer-props;
        }
      }
    }
    uses service-validations-def;
    uses failover-fallback-dualwan-def;
  }

  grouping failover-fallback-dualwan-def {
    container failover-fallback-service {
      list failover-fallback {
        key "transaction-id";
        leaf sequence-number {
          type string;
          default "89";
          description
            "sequence-number";
          config false;
        }
        leaf transaction-id {
          type string-no-space;
          description
            "Enter Transaction Name
             This is an internal field for Anuta NCX";
        }
        leaf operation-type {
          type enumeration {
            enum "failover";
            enum "fallback";
            enum "switch-off-dps";
            enum "switch-on-dps";
          }
          mandatory true;
          description
            "Select operation type:
             - Failover: Apply policy on WAN eBGP peer(s) configured under cpe-primary-wan & cpe-secondary-wan or selectively
             - Fallback: Restore original policy on WAN eBGP peer(s) configured under cpe-primary-wan & cpe-secondary-wan
             - Switch-Off-DPS: Apply CoPP policy to disable OSPF adjancecy on Tunnel100
             - Switch-On-DPS:  Remove CoPP policy to re-enable OSPF adjacency on Tunnel100";
        }
        leaf selective-failover {
          type enumeration {
            enum "primary-cpe-primary-wan-link";
            enum "primary-cpe-secondary-wan-link";
          }
          description
            "primary-cpe-primary-wan-link
             primary-cpe-secondary-wan-link
            ";
          when "../operation-type = 'failover'";
        }
        leaf created-by {
          type string;
          description
            "string";
          config false;
        }
        leaf created-on {
          type string;
          description
            "string";
          config false;
        }
      }
    }
  }

  grouping dc-domain-def {
    uses sm:service-def {
      refine "name" {
        config false;
      }
      refine "service-sequence" {
        config false;
      }
      refine "resource-pool" {
        n-ext-ui:ncx-ext-allowed-vals "/rp:resource-pools/rp:resource-pool[rp:parent-resource-pool=current()/../../../resource-pool]/rp:name";
        mandatory true;
      }
    }
    container cpe {
      uses vrf:vrouter-def {
        refine "internal-id" {
          default "cpe";
          config false;
        }
        refine "name" {
          default "cpe";
        }
        refine "vrf-name" {
          config false;
        }
        refine "resource-id" {
          config false;
        }
        refine "sequence-number" {
          default "1";
          config false;
        }
        refine "deploy-on" {
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:routes/route[dest-ip-address=current()/../../dest-ip-address]/options[id=current()/../id]/vrf-name";
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "device-ip";
        mandatory true;
      }
      uses vrouter-local-def;
      leaf level {
        type uint8;
        description
          "0..255";
        default "2";
        config false;
      }
    }
    container wan {
      uses enf:external-network-def {
        refine "internal-id" {
          default "wan";
          config false;
        }
        refine "sequence-number" {
          default "41";
          config false;
        }
        refine "resource-id" {
          config false;
        }
        refine "deploy-on" {
          config false;
        }
        refine "name" {
          default "wan";
        }
      }
      leaf level {
        type uint8;
        description
          "0..255";
        default "1";
        config false;
      }
      leaf wan-connectivity {
        type enumeration {
          enum "MPLS";
          enum "INET";
        }
        description
          "MPLS
           INET
          ";
        default "MPLS";
      }
    }
    container cpe-wan {
      uses ic:interconnect-def {
        refine "name" {
          default "cpe-wan";
          config false;
        }
        refine "deploy-on" {
          config false;
        }
        refine "resource-id" {
          config false;
        }
        refine "interconnect-name" {
          default "cpe-wan";
        }
        refine "sequence-number" {
          default "42";
          config false;
        }
        refine "internal-id" {
          config false;
        }
        refine "type" {
          config false;
        }
      }
      leaf endpoint1 {
        n-ext:end-point;
        type leafref {
          path "../../wan/internal-id";
        }
        description
          "Reference to the endpoint of the interconnect";
        default "wan";
        config false;
      }
      leaf endpoint2 {
        n-ext:end-point;
        type leafref {
          path "../../cpe/internal-id";
        }
        description
          "Reference to the endpoint of the interconnect";
        default "cpe";
        config false;
      }
      uses ic-local-props {
        refine "cidr" {
          mandatory false;
          config false;
        }
        refine "inbound-policy" {
          config false;
        }
        //refining as per cpe/ip-address
        refine "outbound-policy" {
          n-ext:maps-to "/ac:devices/ac:device[ac:id=current()/../../cpe/device-ip]/qos:policy-maps/policy-map/name";
        }
        refine "policy-name" {
          n-ext:maps-to "/ac:devices/ac:device[ac:id=current()/../../cpe/device-ip]/qos:policy-maps/policy-map/name";
        }
        refine "shape-average" {
          n-ext:maps-to "/ac:devices/ac:device[ac:id=current()/../../cpe/device-ip]/qos:policy-maps/policy-map[name=current()/../policy-name]/class-entry/shape-average";
        }
        refine "child-qos-policy" {
          n-ext:maps-to "/ac:devices/ac:device[ac:id=current()/../../cpe/device-ip]/qos:policy-maps/policy-map[name=current()/../policy-name]/class-entry/service-policy";
        }
        refine "speed" {
          n-ext:maps-to "/ac:devices/ac:device[ac:id=current()/../../cpe/device-ip]/if:interfaces/interface/link-speed";
        }
        refine "duplex" {
          n-ext:maps-to "/ac:devices/ac:device[ac:id=current()/../../cpe/device-ip]/if:interfaces/interface/duplex";
        }
        refine "in-queue-length" {
          n-ext:maps-to "/ac:devices/ac:device[ac:id=current()/../../cpe/device-ip]/if:interfaces/interface/in-queue-length";
        }
        refine "out-queue-length" {
          n-ext:maps-to "/ac:devices/ac:device[ac:id=current()/../../cpe/device-ip]/if:interfaces/interface/out-queue-length";
        }
      }
      list end-points {
        leaf sequence-number {
          type string;
          default "43";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          //n-ext:maps-to "/ac:devices/ac:device[ac:id=current()/../device-ip]/dmvpn:dmvpntunnels/dmvpntunnel/name";
          when "../interface-type = 'Tunnel'";
        }
        leaf p2p {
          type boolean;
          description
            "Check if P2P DMVPN Tunnel";
          when "../interface-type = 'Tunnel'";
        }
        leaf tunnel-interface-ip-address {
          type inet:ipv4-address;
          description
            "Enter Tunnel Interface IP Address";
          n-ext:maps-to "/ac:devices/ac:device[ac:id=current()/../device-ip]/dmvpn:dmvpntunnels/dmvpntunnel[name=current()/../tunnel-interface-id]/ipaddress";
          when "../interface-type = 'Tunnel'";
        }
        leaf tunnel-interface-mask {
          type inet:ipv4-address;
          description
            "Enter GRE Tunnel Interface Subnet Mask
             This is only required for non-DMVPN Tunnel Interface (eg: Zscaler)
            ";
          n-ext:maps-to "/ac:devices/ac:device[ac:id=current()/../device-ip]/dmvpn:dmvpntunnels/dmvpntunnel[name=current()/../tunnel-interface-id]/netmask";
          when "../interface-type = 'Tunnel'";
        }
        leaf tunnel-interface-destination {
          type inet:ipv4-address;
          description
            "Enter GRE Tunnel Interface Destination
             This is only required for non-DMVPN Tunnel Interface (eg: Zscaler)
            ";
          n-ext:maps-to "/ac:devices/ac:device[ac:id=current()/../device-ip]/dmvpn:dmvpntunnels/dmvpntunnel[name=current()/../tunnel-interface-id]/tunnel-destination";
          when "../interface-type = 'Tunnel'";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          n-ext:maps-to "/ac:devices/ac:device[ac:id=current()/../device-ip]/dmvpn:dmvpntunnels/dmvpntunnel[name=current()/../tunnel-interface-id]/tunnel-source";
          when "../interface-type = 'Tunnel'";
        }
        leaf tunnel-bandwidth {
          type uint32 {
            range "1..100000000";
          }
          description
            "Enter Tunnel Interface Bandwidth";
          units "Kbps";
          n-ext:maps-to "/ac:devices/ac:device[ac:id=current()/../device-ip]/dmvpn:dmvpntunnels/dmvpntunnel[name=current()/../tunnel-interface-id]/bandwidth";
          when "../interface-type = 'Tunnel'";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "44";
            description
              "sequence-number";
            config false;
          }
          key "name";
          uses eigrp-props-end;
        }
        list bgp-peers {
          leaf sequence-number {
            type string;
            default "45";
            description
              "sequence-number";
            config false;
          }
          key "BGP-peer-name";
          uses bgp-peer-props;
        }
      }
    }
    container lan {
      uses vnf:virtual-network-def {
        refine "internal-id" {
          default "lan";
          config false;
        }
        refine "sequence-number" {
          default "46";
          config false;
        }
        refine "resource-id" {
          config false;
        }
        refine "deploy-on" {
          config false;
        }
        refine "name" {
          default "lan";
        }
      }
      leaf level {
        type uint8;
        description
          "0..255";
        default "4";
        config false;
      }
      list switches {
        leaf sequence-number {
          type string;
          default "130";
          description
            "sequence-number";
          config false;
        }
        key "device";
        uses switch-def;
      }
    }
    container cpe-lan {
      uses ic:interconnect-def {
        refine "name" {
          default "cpe-lan";
          config false;
        }
        refine "deploy-on" {
          config false;
        }
        refine "resource-id" {
          config false;
        }
        refine "interconnect-name" {
          default "cpe-lan";
        }
        refine "sequence-number" {
          default "47";
          config false;
        }
        refine "internal-id" {
          config false;
        }
        refine "type" {
          config false;
        }
      }
      leaf endpoint1 {
        n-ext:end-point;
        type leafref {
          path "../../cpe/internal-id";
        }
        description
          "Reference to the endpoint of the interconnect";
        default "cpe";
        config false;
      }
      leaf endpoint2 {
        n-ext:end-point;
        type leafref {
          path "../../lan/internal-id";
        }
        description
          "Reference to the endpoint of the interconnect";
        default "lan";
        config false;
      }
      uses ic-local-props {
        refine "hierarchical-outbound-policy" {
          config false;
        }
        refine "outbound-policy" {
          config false;
        }
        refine "policy-name" {
          config false;
        }
        refine "shape-average" {
          config false;
        }
        refine "child-qos-policy" {
          config false;
        }
        refine "inbound-policy" {
          config false;
        }
        refine "cidr" {
          mandatory false;
          config false;
        }
        refine "auto-negotiation" {
          config false;
        }
        refine "speed" {
          config false;
        }
        refine "duplex" {
          config false;
        }
        refine "load-interval" {
          config false;
        }
        refine "hold-queue-in" {
          config false;
        }
        refine "hold-queue-out" {
          config false;
        }
      }
      list lan-profile {
        key "profile-name";
        leaf profile-name {
          type string;
          description
            "string";
        }
        uses ic-local {
          refine "cidr" {
            mandatory false;
          }
          refine "inbound-policy" {
            //n-ext:maps-to "/ac:devices/ac:device[ac:id=current()/../../cpe/device-ip]/qos:policy-maps/policy-map/name";
            n-ext:maps-to "/ac:devices/ac:device[ac:id=current()/../../../cpe/device-ip]/interface:interfaces/interface/inbound-qos";
          }
          refine "hierarchical-policy" {
            //n-ext:maps-to "/ac:devices/ac:device[ac:id=current()/../../cpe/device-ip]/qos:policy-maps/policy-map/name";
            n-ext:maps-to "/ac:devices/ac:device[ac:id=current()/../../../cpe/device-ip]/interface:interfaces/interface/inbound-qos";
          }
          refine "outbound-lan-policy" {
            //n-ext:maps-to "/ac:devices/ac:device[ac:id=current()/../../cpe/device-ip]/qos:policy-maps/policy-map/name";
            n-ext:maps-to "/ac:devices/ac:device[ac:id=current()/../../../cpe/device-ip]/interface:interfaces/interface/outbound-qos";
          }
          refine "hierarchical-egress-policy" {
            //n-ext:maps-to "/ac:devices/ac:device[ac:id=current()/../../cpe/device-ip]/qos:policy-maps/policy-map/name";
            n-ext:maps-to "/ac:devices/ac:device[ac:id=current()/../../../cpe/device-ip]/interface:interfaces/interface/outbound-qos";
          }
          refine "speed" {
            n-ext:maps-to "/ac:devices/ac:device[ac:id=current()/../../../cpe/device-ip]/if:interfaces/interface/link-speed";
          }
          refine "duplex" {
            n-ext:maps-to "/ac:devices/ac:device[ac:id=current()/../../../cpe/device-ip]/if:interfaces/interface/duplex";
          }
          refine "in-queue-length" {
            n-ext:maps-to "/ac:devices/ac:device[ac:id=current()/../../../cpe/device-ip]/if:interfaces/interface/in-queue-length";
          }
          refine "out-queue-length" {
            n-ext:maps-to "/ac:devices/ac:device[ac:id=current()/../../../cpe/device-ip]/if:interfaces/interface/out-queue-length";
          }
        }
      }
      list end-points {
        leaf sequence-number {
          type string;
          default "48";
          description
            "sequence-number";
          config false;
        }
        key "endpoint-name";
        leaf profile-name {
          type string;
          //type leafref {
          //path "/ac:services/cpedeployment:managed-cpe-services/customer[name=current()/../../../../../name]/single-cpe-site/single-cpe-site-services[site-name=current()/../../../site-name]/cpe-lan/lan-profile/profile-name";
          //}
          description
            "string";
          //mandatory true;
        }
        uses end-point-props;
        list eigrp {
          leaf sequence-number {
            type string;
            default "49";
            description
              "sequence-number";
            config false;
          }
          key "name";
          uses eigrp-props-end;
        }
        list bgp-peers {
          leaf sequence-number {
            type string;
            default "50";
            description
              "sequence-number";
            config false;
          }
          key "BGP-peer-name";
          uses bgp-peer-props;
        }
      }
    }
    uses service-validations-def;
    uses failover-fallback-def;
  }

  grouping failover-fallback-def {
    container failover-fallback-service {
      list failover-fallback {
        key "transaction-id";
        leaf sequence-number {
          type string;
          default "88";
          description
            "sequence-number";
          config false;
        }
        leaf transaction-id {
          type string-no-space;
          description
            "Enter Transaction Name
             This is an internal field used by Anuta NCX";
        }
        leaf operation-type {
          type enumeration {
            enum "failover";
            enum "fallback";
            enum "switch-off-dps";
            enum "switch-on-dps";
          }
          mandatory true;
          description
            "Select operation type:
             - Failover: Selection of one eBGP peer mandatory to apply failover policy
             - Fallback: Selection of one eBGP peer mandatory to apply fallover policy
             - Switch-Off-DPS: Apply CoPP policy to disable OSPF adjancecy on Tunnel100
             - Switch-On-DPS:  Remove CoPP policy to re-enable OSPF adjacency on Tunnel100";
        }
        leaf wan-ebgp-neighbor {
          type leafref {
            path "/ac:services/cpedeployment:managed-cpe-services/customer[name=current()/../../../../../name]/single-cpe-site/single-cpe-site-services[site-name=current()/../../../site-name]/cpe-wan/end-points/bgp-peers/peer-ip";
          }
          description
            "Select WAN eBGP peer under container cpe-wan on which to perform failover/fallback operation";
          when "../operation-type = 'failover' or ../operation-type = 'fallback'";
          mandatory true;
        }
        leaf created-by {
          type string;
          description
            "string";
          config false;
        }
        leaf created-on {
          type string;
          description
            "string";
          config false;
        }
      }
    }
  }

  grouping switch-def {
    leaf device {
      type leafref {
        path "/rp:resource-pools/rp:resource-pool[rp:name=current()/../../../resource-pool]/rp:device/rp:id";
      }
      description
        "Select Layer2 Switch Device";
      mandatory true;
    }
    list spanning-tree {
      key "options";
      leaf sequence-number {
        type string;
        default "131";
        description
          "sequence-number";
        config false;
      }
      leaf options {
        type enumeration {
          enum "mode";
          enum "vlan";
        }
        description
          "Select Spanning-Tree configuration options:
           - Mode will allow you to configure Spanning-Tree mode
           - VLAN will allow you to configure Spanning-Tree VLAN instance";
      }
      leaf mode {
        type enumeration {
          enum "mst";
          enum "pvst";
          enum "rapid-pvst";
        }
        description
          "Select Spanning-Tree Mode";
        when "../options = 'mode' ";
        n-ext:maps-to "/ac:devices/ac:device[ac:id=current()/../../device-ip]/basicDeviceConfigs:spanning-tree/mode/mode";
      }
      leaf extend-system-id {
        type boolean;
        description
          "Check to enable Spanning-Tree Extend System ID";
        when "../mode = 'pvst' or ../mode = 'rapid-pvst' ";
        n-ext:maps-to "/ac:devices/ac:device[ac:id=current()/../../device-ip]/basicDeviceConfigs:spanning-tree/mode[mode=current()/../mode]/extend-system-id";
      }
      leaf vlan-range {
        type string-no-lead-trail-space;
        description
          "Enter Spanning-Tree VLAN range";
        when "../options = 'vlan'";
        n-ext:maps-to "/ac:devices/ac:device[ac:id=current()/../../device-ip]/basicDeviceConfigs:spanning-tree/vlan/vlan";
      }
      leaf priority {
        type uint16 {
          range "0..61440";
        }
        description
          "Enter Spanning-Tree priority for VLAN instance(s)";
        when "../options = 'vlan'";
        n-ext:maps-to "/ac:devices/ac:device[ac:id=current()/../../device-ip]/basicDeviceConfigs:spanning-tree/vlan[vlan=current()/../vlan]/priority";
      }
    }
    list vlan {
      key "vlan-id";
      leaf sequence-number {
        type string;
        default "132";
        description
          "sequence-number";
        config false;
      }
      leaf vlan-id {
        type uint16 {
          range "1..4094";
        }
        description
          "Enter VLAN ID to configure on Layer2 Switch";
        n-ext:maps-to "/ac:devices/ac:device[ac:id=current()/../../device-ip]/l2:vlans/vlan/id";
      }
      leaf name {
        type string-no-space;
        description
          "Enter VLAN name to configure on Layer2 Switch";
        n-ext:maps-to "/ac:devices/ac:device[ac:id=current()/../../device-ip]/l2:vlans/vlan[id=current()/../vlan-id]/name";
      }
    }
    list interface {
      key "name";
      leaf sequence-number {
        type string;
        default "133";
        description
          "sequence-number";
        config false;
      }
      leaf name {
        type string-no-space;
        description
          "Enter Interface Name
           This is an internal field for Anuta NCX";
      }
      leaf interface-type {
        type interface-type;
        description
          "Select Interface Type";
        mandatory true;
      }
      leaf interface-name {
        type leafref {
          path "/ac:devices/ac:device[ac:id=current()/../../device]/if:interfaces/if:interface/if:name";
        }
        description
          "Select Interface Name";
        n-ext:maps-to "/ac:devices/ac:device[ac:id=current()/../../device]/if:interfaces/interface/name";
        when "../interface-type =  'Physical'";
      }
      leaf vlan-id {
        type uint32 {
          range "1..4096";
        }
        description
          "Enter SVI interface VLAN ID";
        n-ext:maps-to "/ac:devices/ac:device[ac:id=current()/../../device]/if:interfaces/interface[if-type=l2vlan]/long-name";
        when "../interface-type =  'SVI'";
      }
      leaf cidr {
        type leafref {
          path "/ip:ipaddress-pools/ip:ipaddress-pool/ip:name";
        }
        n-ext-ui:ncx-ext-pagination "paginate";
        description
          "Select IPAM Subnet to configure on SVI";
        mandatory true;
        when "../interface-type =  'SVI'";
      }
      leaf interface-ip {
        type inet:ipv4-address;
        description
          "Enter SVI IPv4 Address";
        n-ext:maps-to "/ac:devices/ac:device[ac:id=current()/../../device]/if:interfaces/interface[if-type=l2vlan]/ip-address";
        when "../interface-type =  'SVI'";
      }
      leaf interface-description {
        type string-no-lead-trail-space;
        description
          "Enter Interface Description";
        n-ext:maps-to "/ac:devices/ac:device[ac:id=current()/../../device]/if:interfaces/interface[long-name=current()/../interface-name]/description";
        n-ext:maps-to "/ac:devices/ac:device[ac:id=current()/../../device]/if:interfaces/interface[if-type=l2vlan]/description";
      }
      list switchport {
        key "name";
        leaf sequence-number {
          type string;
          default "134";
          description
            "sequence-number";
          config false;
        }
        leaf name {
          type string;
          description
            "Enter Layer2 switch port name
             This is an internal field for Anuta NCX";
        }
        leaf options {
          type enumeration {
            enum "port-security";
            enum "trunk";
            enum "access";
            enum "mode";
          }
          description
            "Select Layer2 switch option to configure";
        }
        leaf port-security-options {
          type enumeration {
            enum "maximum";
            enum "violation";
          }
          description
            "Select switchport port security option to configure";
          when "../options =  'port-security'";
        }
        leaf maximum {
          type uint16 {
            range "1..5120";
          }
          description
            "Enter switchport port security maximum MAC addresses allowed";
          when "../options =  'port-security' and ../port-security-options =  'maximum'";
          n-ext:maps-to "/ac:devices/ac:device[ac:id=current()/../../../device-ip]/if:interfaces/interface[long-name=current()/../../interface-name]/if-ext:port-security/if-ext:port-security-maximum/if-ext:portSecurityMaximum";
        }
        leaf violation {
          type enumeration {
            enum "protect";
            enum "restrict";
            enum "shutdown";
          }
          description
            "Select switchport port security violation policy";
          when "../options =  'port-security' and ../port-security-options =  'violation'";
          n-ext:maps-to "/ac:devices/ac:device[ac:id=current()/../../../device-ip]/if:interfaces/interface[long-name=current()/../../interface-name]/if-ext:port-security/if-ext:portViolation";
        }
        leaf trunk-options {
          type enumeration {
            enum "encapsulation";
            enum "allowed";
          }
          description
            "Select 802.1q trunk option to configure on switchport";
          when "../options =  'trunk'";
        }
        leaf encapsulation {
          type enumeration {
            enum "dot1q";
          }
          description
            "802.1q encapsulation by default";
          when "../options =  'trunk' and ../trunk-options =  'encapsulation'";
        }
        leaf allowed-vlan {
          type string-no-lead-trail-space;
          description
            "Enter 802.1q trunk allowed vlan(s)";
          when "../options =  'trunk' and ../trunk-options =  'allowed'";
        }
        leaf access {
          type union {
            type enumeration {
              enum "dynamic";
            }
            type string-no-lead-trail-space;
          }
          description
            "Enter switchport VLAN access ID";
          n-ext:maps-to "/ac:devices/ac:device[ac:id=current()/../../../device-ip]/if:interfaces/interface[long-name=current()/../../interface-name]/allowed-vlans/vlan/id";
          when "../options =  'access'";
        }
        leaf mode {
          type enumeration {
            enum "access";
            enum "trunk";
          }
          description
            "Enter switchport mode";
          when "../options =  'mode'";
        }
      }
    }
  }

  grouping eigrp-props-end {
    leaf name {
      type string;
      description
        "Enter EIGRP InterfaceProcess Name
         This is an internal field for Anuta NCX
        ";
      //n-ext:maps-to "/ac:devices/device[id=current()/../../device-ip]/l3features:eigrp/router-eigrp/eigrp-name";
    }
    leaf as-number {
      type uint32;
      description
        "Enter EIGRP AS Number";
      //n-ext:maps-to "/ac:devices/device[id=current()/../../../device-ip]/l3features:eigrp/router-eigrp[eigrp-name=current()/../name]/address-family/as-number";
      //n-ext:maps-to "/ac:devices/device[id=current()/../../device-ip]/l3:vrfs/vrf[name=current()/../../vrf-name]/router-eigrp/process-id";
      n-ext:maps-to "/ac:devices/ac:device[ac:id=current()/../../device-ip]/if:interfaces/interface[long-name=current()/../../interface-name]/eigrp/as-number/as-number";
    }
    leaf in-route-map {
      type leafref {
        path "/ac:services/cpedeployment:managed-cpe-services/customer[name=current()/../../../../../../name]/route-maps/route-map/route-map-name";
      }
      description
        "Distribute List Inbound Route-Map";
      //n-ext:maps-to "/ac:devices/device[id=current()/../../../device-ip]/l3features:eigrp/router-eigrp[eigrp-name=current()/../name]/address-family/as-number";
      n-ext:maps-to "/ac:devices/ac:device[ac:id=current()/../../device-ip]/l3:vrfs/vrf[name=current()/../../vrf]/router-eigrp/eigrp/distribute-list[filter=in]/route-map";
      n-ext:maps-to "/ac:devices/ac:device[ac:id=current()/../../device-ip]/l3:vrfs/vrf[name=GLOBAL]/router-eigrp/eigrp/distribute-list[filter=in]/route-map";
      n-ext:maps-to "/ac:devices/ac:device[ac:id=current()/../../device-ip]/l3:vrfs/vrf[name=current()/../../ivrf]/router-eigrp/eigrp/distribute-list[filter=in]/route-map";
      //n-ext:maps-to "/ac:devices/device[id=current()/../../../device-ip]/l3:vrfs/vrf[name=current()/../../vrf-name]/router-eigrp/eigrp/distribute-list/route-map";
    }
    leaf out-route-map {
      type leafref {
        path "/ac:services/cpedeployment:managed-cpe-services/customer[name=current()/../../../../../../name]/route-maps/route-map/route-map-name";
      }
      description
        "Distribute List Outbound Route-Map";
      //n-ext:maps-to "/ac:devices/device[id=current()/../../../device-ip]/l3features:eigrp/router-eigrp[eigrp-name=current()/../name]/address-family/as-number";
      n-ext:maps-to "/ac:devices/ac:device[ac:id=current()/../../device-ip]/l3:vrfs/vrf[name=current()/../../vrf]/router-eigrp/eigrp/distribute-list[filter=out]/route-map";
      n-ext:maps-to "/ac:devices/ac:device[ac:id=current()/../../device-ip]/l3:vrfs/vrf[name=GLOBAL]/router-eigrp/eigrp/distribute-list[filter=out]/route-map";
      n-ext:maps-to "/ac:devices/ac:device[ac:id=current()/../../device-ip]/l3:vrfs/vrf[name=current()/../../ivrf]/router-eigrp/eigrp/distribute-list[filter=out]/route-map";
    }
    leaf passive-interface {
      type boolean;
      description
        "Check if Interface should be configured as EIGRP passive interface";
      //n-ext:maps-to "/ac:devices/device[id=current()/../../../device-ip]/l3features:eigrp/router-eigrp[eigrp-name=current()/../name]/address-family[as-number=current()/../as-number]/af-interface/passive-interface";
      n-ext:maps-to "/ac:devices/ac:device[ac:id=current()/../../device-ip]/l3:vrfs/vrf[name=current()/../../vrf]/router-eigrp/eigrp/passive-interface/passive-interface";
      n-ext:maps-to "/ac:devices/ac:device[ac:id=current()/../../device-ip]/l3:vrfs/vrf[name=GLOBAL]/router-eigrp/eigrp/passive-interface/passive-interface";
      n-ext:maps-to "/ac:devices/ac:device[ac:id=current()/../../device-ip]/l3:vrfs/vrf[name=current()/../../ivrf]/router-eigrp/eigrp/passive-interface/passive-interface";
    }
    leaf key-chain {
      type leafref {
        path "/ac:services/cpedeployment:managed-cpe-services/customer[name=current()/../../../../../../name]/key-chain/router-key-chain/key-chain-name";
      }
      description
        "Select Key-Chain Profile";
      //n-ext:maps-to "/ac:devices/device[id=current()/../../../device-ip]/l3features:eigrp/router-eigrp[eigrp-name=current()/../name]/address-family[as-number=current()/../as-number]/af-interface/key-chain";
      n-ext:maps-to "/ac:devices/ac:device[ac:id=current()/../../device-ip]/if:interfaces/interface[long-name=current()/../../interface-name]/eigrp/as-number[as-number=current()/../as-number]/key-chain";
    }
    leaf hello-interval {
      type uint16 {
        range "1..65535";
      }
      description
        "Enter EIGRP Hello Interval";
      //n-ext:maps-to "/ac:devices/device[id=current()/../../../device-ip]/l3features:eigrp/router-eigrp[eigrp-name=current()/../name]/address-family[as-number=current()/../as-number]/af-interface/hello-interval";
      n-ext:maps-to "/ac:devices/ac:device[ac:id=current()/../../device-ip]/if:interfaces/interface[long-name=current()/../../interface-name]/eigrp/as-number[as-number=current()/../as-number]/hello-interval";
    }
    leaf hold-time {
      type uint16 {
        range "1..65535";
      }
      description
        "Enter EIGRP Hold Time";
      //n-ext:maps-to "/ac:devices/device[id=current()/../../../device-ip]/l3features:eigrp/router-eigrp[eigrp-name=current()/../name]/address-family[as-number=current()/../as-number]/af-interface/hold-time";
      n-ext:maps-to "/ac:devices/ac:device[ac:id=current()/../../device-ip]/if:interfaces/interface[long-name=current()/../../interface-name]/eigrp/as-number[as-number=current()/../as-number]/hold-time";
    }
    leaf split-horizon {
      type boolean;
      description
        "Check if EIGRP Split-Horizon should be enabled on the interface";
      //n-ext:maps-to "/ac:devices/device[id=current()/../../../device-ip]/l3features:eigrp/router-eigrp[eigrp-name=current()/../name]/address-family[as-number=current()/../as-number]/af-interface/split-horizon";
      n-ext:maps-to "/ac:devices/ac:device[ac:id=current()/../../device-ip]/if:interfaces/interface[long-name=current()/../../interface-name]/eigrp/as-number[as-number=current()/../as-number]/split-horizon";
    }
    list summary-network {
      key "prefix";
      leaf sequence-number {
        type string;
        default "95";
        description
          "sequence-number";
        config false;
      }
      leaf prefix {
        type inet:ipv4-prefix;
        description
          "Enter EIGRP Summary IPv4 prefix (Eg: 10.0.0.0/16)";
        n-ext:maps-to "/ac:devices/ac:device[ac:id=current()/../../../device-ip]/if:interfaces/interface[long-name=current()/../../../interface-name]/eigrp/as-number[as-number=current()/../../as-number]/summary-network";
        //n-ext:maps-to "/ac:devices/device[id=current()/../../../device-ip]/if:interfaces/interface[long-name=current()/../../../interface-name]/eigrp/as-number[as-number=current()/../../as-number]/summary-network/ip-address";
        //n-ext:maps-to "/ac:devices/device[id=current()/../../../device-ip]/if:interfaces/interface[long-name=current()/../../../interface-name]/eigrp/as-number[as-number=current()/../../as-number]/summary-network/netmask";
        n-ext:prefix-maps-to "ip-address,netmask";
      }
      leaf summary-metric {
        type boolean;
        description
          "Enter EIGRP Summary Route Metric";
      }
      leaf bandwidth-metric {
        type uint64 {
          range "1..4294967295";
        }
        description
          "Enter EIGRP Summary Route Bandwidth Metric";
        when "../summary-metric = 'true' ";
        //n-ext:maps-to "/ac:devices/device[id=current()/../../../device-ip]/l3features:eigrp/router-eigrp[eigrp-name=current()/../name]/address-family[as-number=current()/../as-number]/summary-metric/bandwidth-metric";
        n-ext:maps-to "/ac:devices/ac:device[ac:id=current()/../../../device-ip]/l3:vrfs/vrf[name=current()/../../../vrf]/router-eigrp/eigrp[process-id=current()/../../as-number]/summary-metric/bandwidth-metric";
        n-ext:maps-to "/ac:devices/ac:device[ac:id=current()/../../../device-ip]/l3:vrfs/vrf[name=GLOBAL]/router-eigrp/eigrp[process-id=current()/../../as-number]/summary-metric/bandwidth-metric";
        n-ext:maps-to "/ac:devices/ac:device[ac:id=current()/../../../device-ip]/l3:vrfs/vrf[name=current()/../../../ivrf]/router-eigrp/eigrp[process-id=current()/../../as-number]/summary-metric/bandwidth-metric";
      }
      leaf delay-metric {
        type uint64 {
          range "0..4294967295";
        }
        description
          "Enter EIGRP Summary Route Delay Metric";
        when "../summary-metric = 'true' ";
        //n-ext:maps-to "/ac:devices/device[id=current()/../../../device-ip]/l3features:eigrp/router-eigrp[eigrp-name=current()/../name]/address-family[as-number=current()/../as-number]/summary-metric/delay-metric";
        n-ext:maps-to "/ac:devices/ac:device[ac:id=current()/../../../device-ip]/l3:vrfs/vrf[name=current()/../../../vrf]/router-eigrp/eigrp[process-id=current()/../../as-number]/summary-metric/delay-metric";
        n-ext:maps-to "/ac:devices/ac:device[ac:id=current()/../../../device-ip]/l3:vrfs/vrf[name=GLOBAL]/router-eigrp/eigrp[process-id=current()/../../as-number]/summary-metric/delay-metric";
        n-ext:maps-to "/ac:devices/ac:device[ac:id=current()/../../../device-ip]/l3:vrfs/vrf[name=current()/../../../ivrf]/router-eigrp/eigrp[process-id=current()/../../as-number]/summary-metric/delay-metric";
      }
      leaf reliability-metric {
        type uint16 {
          range "0..255";
        }
        description
          "Enter EIGRP Summary Route Reliability Metric";
        when "../summary-metric = 'true' ";
        //n-ext:maps-to "/ac:devices/device[id=current()/../../../device-ip]/l3features:eigrp/router-eigrp[eigrp-name=current()/../name]/address-family[as-number=current()/../as-number]/summary-metric/reliability-metric";
        n-ext:maps-to "/ac:devices/ac:device[ac:id=current()/../../../device-ip]/l3:vrfs/vrf[name=current()/../../../vrf]/router-eigrp/eigrp[process-id=current()/../../as-number]/summary-metric/reliability-metric";
        n-ext:maps-to "/ac:devices/ac:device[ac:id=current()/../../../device-ip]/l3:vrfs/vrf[name=GLOBAL]/router-eigrp/eigrp[process-id=current()/../../as-number]/summary-metric/reliability-metric";
        n-ext:maps-to "/ac:devices/ac:device[ac:id=current()/../../../device-ip]/l3:vrfs/vrf[name=current()/../../../ivrf]/router-eigrp/eigrp[process-id=current()/../../as-number]/summary-metric/reliability-metric";
      }
      leaf load-metric {
        type uint16 {
          range "1..255";
        }
        description
          "Enter EIGRP Summary Route Load Metric";
        when "../summary-metric = 'true' ";
        //n-ext:maps-to "/ac:devices/device[id=current()/../../../device-ip]/l3features:eigrp/router-eigrp[eigrp-name=current()/../name]/address-family[as-number=current()/../as-number]/summary-metric/load-metric";
        n-ext:maps-to "/ac:devices/ac:device[ac:id=current()/../../../device-ip]/l3:vrfs/vrf[name=current()/../../../vrf]/router-eigrp/eigrp[process-id=current()/../../as-number]/summary-metric/load-metric";
        n-ext:maps-to "/ac:devices/ac:device[ac:id=current()/../../../device-ip]/l3:vrfs/vrf[name=GLOBAL]/router-eigrp/eigrp[process-id=current()/../../as-number]/summary-metric/load-metric";
        n-ext:maps-to "/ac:devices/ac:device[ac:id=current()/../../../device-ip]/l3:vrfs/vrf[name=current()/../../../ivrf]/router-eigrp/eigrp[process-id=current()/../../as-number]/summary-metric/load-metric";
      }
      leaf mtu {
        type uint16 {
          range "1..65535";
        }
        description
          "Enter EIGRP Summary Route MTU Metric";
        when "../summary-metric = 'true' ";
        //n-ext:maps-to "/ac:devices/device[id=current()/../../../device-ip]/l3features:eigrp/router-eigrp[eigrp-name=current()/../name]/address-family[as-number=current()/../as-number]/summary-metric/mtu";
        n-ext:maps-to "/ac:devices/ac:device[ac:id=current()/../../../device-ip]/l3:vrfs/vrf[name=current()/../../../vrf]/router-eigrp/eigrp[process-id=current()/../../as-number]/summary-metric/mtu";
        n-ext:maps-to "/ac:devices/ac:device[ac:id=current()/../../../device-ip]/l3:vrfs/vrf[name=GLOBAL]/router-eigrp/eigrp[process-id=current()/../../as-number]/summary-metric/mtu";
        n-ext:maps-to "/ac:devices/ac:device[ac:id=current()/../../../device-ip]/l3:vrfs/vrf[name=current()/../../../ivrf]/router-eigrp/eigrp[process-id=current()/../../as-number]/summary-metric/mtu";
      }
    }
  }

  grouping dc-domain-dual-def {
    uses sm:service-def {
      refine "name" {
        config false;
      }
      refine "service-sequence" {
        config false;
      }
      refine "resource-pool" {
        n-ext-ui:ncx-ext-allowed-vals "/rp:resource-pools/rp:resource-pool[rp:parent-resource-pool=current()/../../../resource-pool]/rp:name";
        mandatory true;
      }
    }
    container cpe {
      uses vrf:vrouter-def {
        refine "internal-id" {
          default "cpe";
          config false;
        }
        refine "name" {
          default "cpe";
        }
        refine "vrf-name" {
          config false;
        }
        refine "resource-id" {
          config false;
        }
        refine "sequence-number" {
          default "1";
          config false;
        }
        refine "deploy-on" {
          config false;
        }
        refine "static-routes/static-route/dest-ip-address" {
          //config false;
          n-ext:maps-to "/ac:devices/ac:device[ac:id=current()/../../../device-ip]/l3features:routes/route/dest-ip-address";
          n-ext:maps-to "/ac:devices/ac:device[ac:id=current()/../../../device-ip]/l3features:vrfs/vrf[name=DATA]/l3features:routes/route/dest-ip-address";
          n-ext:maps-to "/ac:devices/ac:device[ac:id=current()/../../../device-ip]/l3features:vrfs/vrf[name=DPS]/l3features:routes/route/dest-ip-address";
        }
        refine "static-routes/static-route/dest-mask" {
          //config false;
          n-ext:maps-to "/ac:devices/ac:device[ac:id=current()/../../../device-ip]/l3features:routes/route[dest-ip-address=current()/../dest-ip-address]/dest-mask";
          n-ext:maps-to "/ac:devices/ac:device[ac:id=current()/../../../device-ip]/l3features:vrfs/vrf[name=DATA]/l3features:routes/route[dest-ip-address=current()/../dest-ip-address]/dest-mask";
          n-ext:maps-to "/ac:devices/ac:device[ac:id=current()/../../../device-ip]/l3features:vrfs/vrf[name=DPS]/l3features:routes/route[dest-ip-address=current()/../dest-ip-address]/dest-mask";
        }
        refine "static-routes/static-route/options/id" {
          //config false;
          n-ext:maps-to "/ac:devices/ac:device[ac:id=current()/../../../../device-ip]/l3features:routes/route[dest-ip-address=current()/../../dest-ip-address]/options/id";
          n-ext:maps-to "/ac:devices/ac:device[ac:id=current()/../../../../device-ip]/l3features:vrfs/vrf[name=DATA]/l3features:routes/route[dest-ip-address=current()/../../dest-ip-address]/options/id";
          n-ext:maps-to "/ac:devices/ac:device[ac:id=current()/../../../../device-ip]/l3features:vrfs/vrf[name=DPS]/l3features:routes/route[dest-ip-address=current()/../../dest-ip-address]/options/id";
        }
        refine "static-routes/static-route/options/next-hop-ip" {
          //config false;
          n-ext:maps-to "/ac:devices/ac:device[ac:id=current()/../../../../device-ip]/l3features:routes/route[dest-ip-address=current()/../../dest-ip-address]/options[id=current()/../id]/next-hop-ip";
          n-ext:maps-to "/ac:devices/ac:device[ac:id=current()/../../../../device-ip]/l3features:vrfs/vrf[name=DATA]/l3features:routes/route[dest-ip-address=current()/../../dest-ip-address]/options[id=current()/../id]/next-hop-ip";
          n-ext:maps-to "/ac:devices/ac:device[ac:id=current()/../../../../device-ip]/l3features:vrfs/vrf[name=DPS]/l3features:routes/route[dest-ip-address=current()/../../dest-ip-address]/options[id=current()/../id]/next-hop-ip";
        }
        //refine "static-routes/static-route/options/global-address" {
        //config false;
        //n-ext:maps-to "/ac:devices/device[id=current()/../../../../device-ip]/l3features:routes/route[dest-ip-address=current()/../../dest-ip-address]/options[id=current()/../id]/global-address";
        //}
        refine "static-routes/static-route/options/metric" {
          //config false;
          n-ext:maps-to "/ac:devices/ac:device[ac:id=current()/../../../../device-ip]/l3features:routes/route[dest-ip-address=current()/../../dest-ip-address]/options[id=current()/../id]/metric";
          n-ext:maps-to "/ac:devices/ac:device[ac:id=current()/../../../../device-ip]/l3features:vrfs/vrf[name=DATA]/l3features:routes/route[dest-ip-address=current()/../../dest-ip-address]/options[id=current()/../id]/metric";
          n-ext:maps-to "/ac:devices/ac:device[ac:id=current()/../../../../device-ip]/l3features:vrfs/vrf[name=DPS]/l3features:routes/route[dest-ip-address=current()/../../dest-ip-address]/options[id=current()/../id]/metric";
        }
        refine "static-routes/static-route/options/interface-name" {
          //config false;
          n-ext:maps-to "/ac:devices/ac:device[ac:id=current()/../../../../device-ip]/l3features:routes/route[dest-ip-address=current()/../../dest-ip-address]/options[id=current()/../id]/interface-name";
          n-ext:maps-to "/ac:devices/ac:device[ac:id=current()/../../../../device-ip]/l3features:vrfs/vrf[name=DATA]/l3features:routes/route[dest-ip-address=current()/../../dest-ip-address]/options[id=current()/../id]/interface-name";
          n-ext:maps-to "/ac:devices/ac:device[ac:id=current()/../../../../device-ip]/l3features:vrfs/vrf[name=DPS]/l3features:routes/route[dest-ip-address=current()/../../dest-ip-address]/options[id=current()/../id]/interface-name";
        }
        refine "static-routes/static-route/options/name" {
          //config false;
          n-ext:maps-to "/ac:devices/ac:device[ac:id=current()/../../../../device-ip]/l3features:routes/route[dest-ip-address=current()/../../dest-ip-address]/options[id=current()/../id]/name";
          n-ext:maps-to "/ac:devices/ac:device[ac:id=current()/../../../../device-ip]/l3features:vrfs/vrf[name=DATA]/l3features:routes/route[dest-ip-address=current()/../../dest-ip-address]/options[id=current()/../id]/name";
          n-ext:maps-to "/ac:devices/ac:device[ac:id=current()/../../../../device-ip]/l3features:vrfs/vrf[name=DPS]/l3features:routes/route[dest-ip-address=current()/../../dest-ip-address]/options[id=current()/../id]/name";
        }
        refine "static-routes/static-route/options/vrf" {
          //config false;
          n-ext:maps-to "/ac:devices/ac:device[ac:id=current()/../../../../device-ip]/l3features:routes/route[dest-ip-address=current()/../../dest-ip-address]/options[id=current()/../id]/vrf-name";
          n-ext:maps-to "/ac:devices/ac:device[ac:id=current()/../../../../device-ip]/l3features:vrfs/vrf[name=DATA]/l3features:routes/route[dest-ip-address=current()/../../dest-ip-address]/options[id=current()/../id]/vrf-name";
          n-ext:maps-to "/ac:devices/ac:device[ac:id=current()/../../../../device-ip]/l3features:vrfs/vrf[name=DPS]/l3features:routes/route[dest-ip-address=current()/../../dest-ip-address]/options[id=current()/../id]/vrf-name";
        }
        refine "static-routes/static-route/options/tag" {
          //config false;
          n-ext:maps-to "/ac:devices/ac:device[ac:id=current()/../../../../device-ip]/l3features:routes/route[dest-ip-address=current()/../../dest-ip-address]/options[id=current()/../id]/tag";
          n-ext:maps-to "/ac:devices/ac:device[ac:id=current()/../../../../device-ip]/l3features:vrfs/vrf[name=DATA]/l3features:routes/route[dest-ip-address=current()/../../dest-ip-address]/options[id=current()/../id]/tag";
          n-ext:maps-to "/ac:devices/ac:device[ac:id=current()/../../../../device-ip]/l3features:vrfs/vrf[name=DPS]/l3features:routes/route[dest-ip-address=current()/../../dest-ip-address]/options[id=current()/../id]/tag";
        }
        refine "static-routes/static-route/options/permanent" {
          //config false;
          n-ext:maps-to "/ac:devices/ac:device[ac:id=current()/../../../../device-ip]/l3features:routes/route[dest-ip-address=current()/../../dest-ip-address]/options[id=current()/../id]/permanent";
          n-ext:maps-to "/ac:devices/ac:device[ac:id=current()/../../../../device-ip]/l3features:vrfs/vrf[name=DATA]/l3features:routes/route[dest-ip-address=current()/../../dest-ip-address]/options[id=current()/../id]/permanent";
          n-ext:maps-to "/ac:devices/ac:device[ac:id=current()/../../../../device-ip]/l3features:vrfs/vrf[name=DPS]/l3features:routes/route[dest-ip-address=current()/../../dest-ip-address]/options[id=current()/../id]/permanent";
        }
        refine "static-routes/static-route/options/track" {
          //config false;
          n-ext:maps-to "/ac:devices/ac:device[ac:id=current()/../../../../device-ip]/l3features:routes/route[dest-ip-address=current()/../../dest-ip-address]/options[id=current()/../id]/track";
          n-ext:maps-to "/ac:devices/ac:device[ac:id=current()/../../../../device-ip]/l3features:vrfs/vrf[name=DATA]/l3features:routes/route[dest-ip-address=current()/../../dest-ip-address]/options[id=current()/../id]/track";
          n-ext:maps-to "/ac:devices/ac:device[ac:id=current()/../../../../device-ip]/l3features:vrfs/vrf[name=DPS]/l3features:routes/route[dest-ip-address=current()/../../dest-ip-address]/options[id=current()/../id]/track";
        }
        refine "static-routes/static-route/options/description" {
          //config false;
          n-ext:maps-to "/ac:devices/ac:device[ac:id=current()/../../../../device-ip]/l3features:routes/route[dest-ip-address=current()/../../dest-ip-address]/options[id=current()/../id]/description";
          n-ext:maps-to "/ac:devices/ac:device[ac:id=current()/../../../../device-ip]/l3features:vrfs/vrf[name=DATA]/l3features:routes/route[dest-ip-address=current()/../../dest-ip-address]/options[id=current()/../id]/description";
          n-ext:maps-to "/ac:devices/ac:device[ac:id=current()/../../../../device-ip]/l3features:vrfs/vrf[name=DPS]/l3features:routes/route[dest-ip-address=current()/../../dest-ip-address]/options[id=current()/../id]/description";
        }
        refine "static-routes/static-route/options/global-address" {
          //config false;
          n-ext:maps-to "/ac:devices/ac:device[ac:id=current()/../../../../device-ip]/l3features:vrfs/vrf[name=DATA]/l3features:routes/route[dest-ip-address=current()/../../dest-ip-address]/options[id=current()/../id]/global-address";
          n-ext:maps-to "/ac:devices/ac:device[ac:id=current()/../../../../device-ip]/l3features:vrfs/vrf[name=DPS]/l3features:routes/route[dest-ip-address=current()/../../dest-ip-address]/options[id=current()/../id]/global-address";
        }
        //refine "static-routes/static-route/options/seq-num" {
        //config false;
        //n-ext:maps-to "/ac:devices/device[id=current()/../../../../device-ip]/l3features:routes/route/options/dest-ip-address";
        //}
      }
      leaf rd {
        type string;
        description
          "string";
        config false;
      }
      leaf device-ip {
        type leafref {
          path "/rp:resource-pools/rp:resource-pool[rp:name=current()/../../resource-pool]/rp:device/rp:id";
        }
        description
          "device-ip";
        mandatory true;
      }
      uses vrouter-local-def;
      leaf level {
        type uint8;
        description
          "0..255";
        default "2";
        config false;
      }
    }
    container primary-wan {
      uses enf:external-network-def {
        refine "internal-id" {
          default "primary-wan";
          config false;
        }
        refine "sequence-number" {
          default "41";
          config false;
        }
        refine "resource-id" {
          config false;
        }
        refine "deploy-on" {
          config false;
        }
        refine "name" {
          default "primary-wan";
        }
      }
      leaf level {
        type uint8;
        description
          "0..255";
        default "1";
        config false;
      }
      leaf primary-wan-connectivity {
        type enumeration {
          enum "MPLS";
          enum "INET";
        }
        description
          "MPLS
           INET
          ";
        default "MPLS";
      }
    }
    container cpe-primary-wan {
      uses ic:interconnect-def {
        refine "name" {
          default "cpe-primary-wan";
          config false;
        }
        refine "deploy-on" {
          config false;
        }
        refine "resource-id" {
          config false;
        }
        refine "interconnect-name" {
          default "cpe-primary-wan";
        }
        refine "sequence-number" {
          default "42";
          config false;
        }
        refine "internal-id" {
          config false;
        }
        refine "type" {
          config false;
        }
      }
      leaf endpoint1 {
        n-ext:end-point;
        type leafref {
          path "../../primary-wan/internal-id";
        }
        description
          "Reference to the endpoint of the interconnect";
        default "primary-wan";
        config false;
      }
      leaf endpoint2 {
        n-ext:end-point;
        type leafref {
          path "../../cpe/internal-id";
        }
        description
          "Reference to the endpoint of the interconnect";
        default "cpe";
        config false;
      }
      uses ic-local-props {
        refine "cidr" {
          mandatory false;
          config false;
        }
        refine "inbound-policy" {
          config false;
        }
        //refining as per cpe/ip-address
        refine "outbound-policy" {
          n-ext:maps-to "/ac:devices/ac:device[ac:id=current()/../../cpe/device-ip]/qos:policy-maps/policy-map/name";
        }
        refine "policy-name" {
          n-ext:maps-to "/ac:devices/ac:device[ac:id=current()/../../cpe/device-ip]/qos:policy-maps/policy-map/name";
        }
        refine "shape-average" {
          n-ext:maps-to "/ac:devices/ac:device[ac:id=current()/../../cpe/device-ip]/qos:policy-maps/policy-map[name=current()/../policy-name]/class-entry/shape-average";
        }
        refine "child-qos-policy" {
          n-ext:maps-to "/ac:devices/ac:device[ac:id=current()/../../cpe/device-ip]/qos:policy-maps/policy-map[name=current()/../policy-name]/class-entry/service-policy";
        }
        refine "speed" {
          n-ext:maps-to "/ac:devices/ac:device[ac:id=current()/../../cpe/device-ip]/if:interfaces/interface/link-speed";
        }
        refine "duplex" {
          n-ext:maps-to "/ac:devices/ac:device[ac:id=current()/../../cpe/device-ip]/if:interfaces/interface/duplex";
        }
        refine "in-queue-length" {
          n-ext:maps-to "/ac:devices/ac:device[ac:id=current()/../../cpe/device-ip]/if:interfaces/interface/in-queue-length";
        }
        refine "out-queue-length" {
          n-ext:maps-to "/ac:devices/ac:device[ac:id=current()/../../cpe/device-ip]/if:interfaces/interface/out-queue-length";
        }
      }
      list end-points {
        leaf sequence-number {
          type string;
          default "43";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          //n-ext:maps-to "/ac:devices/ac:device[ac:id=current()/../device-ip]/dmvpn:dmvpntunnels/dmvpntunnel/name";
          when "../interface-type = 'Tunnel'";
        }
        leaf p2p {
          type boolean;
          description
            "Check if P2P DMVPN Tunnel";
          when "../interface-type = 'Tunnel'";
        }
        leaf tunnel-interface-ip-address {
          type inet:ipv4-address;
          description
            "Enter Tunnel Interface IP Address";
          n-ext:maps-to "/ac:devices/ac:device[ac:id=current()/../device-ip]/dmvpn:dmvpntunnels/dmvpntunnel[name=current()/../tunnel-interface-id]/ipaddress";
          when "../interface-type = 'Tunnel'";
        }
        leaf tunnel-interface-mask {
          type inet:ipv4-address;
          description
            "Enter GRE Tunnel Interface Subnet Mask
             This is only required for non-DMVPN Tunnel Interface (eg: Zscaler)
            ";
          n-ext:maps-to "/ac:devices/ac:device[ac:id=current()/../device-ip]/dmvpn:dmvpntunnels/dmvpntunnel[name=current()/../tunnel-interface-id]/netmask";
          when "../interface-type = 'Tunnel'";
        }
        leaf tunnel-interface-destination {
          type inet:ipv4-address;
          description
            "Enter GRE Tunnel Interface Destination
             This is only required for non-DMVPN Tunnel Interface (eg: Zscaler)
            ";
          n-ext:maps-to "/ac:devices/ac:device[ac:id=current()/../device-ip]/dmvpn:dmvpntunnels/dmvpntunnel[name=current()/../tunnel-interface-id]/tunnel-destination";
          when "../interface-type = 'Tunnel'";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          n-ext:maps-to "/ac:devices/ac:device[ac:id=current()/../device-ip]/dmvpn:dmvpntunnels/dmvpntunnel[name=current()/../tunnel-interface-id]/tunnel-source";
          when "../interface-type = 'Tunnel'";
        }
        leaf tunnel-bandwidth {
          type uint32 {
            range "1..100000000";
          }
          description
            "Enter Tunnel Interface Bandwidth";
          units "Kbps";
          n-ext:maps-to "/ac:devices/ac:device[ac:id=current()/../device-ip]/dmvpn:dmvpntunnels/dmvpntunnel[name=current()/../tunnel-interface-id]/bandwidth";
          when "../interface-type = 'Tunnel'";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "44";
            description
              "sequence-number";
            config false;
          }
          key "name";
          uses eigrp-props-end;
        }
        list bgp-peers {
          leaf sequence-number {
            type string;
            default "45";
            description
              "sequence-number";
            config false;
          }
          key "BGP-peer-name";
          uses bgp-peer-props;
        }
      }
    }
    container secondary-wan {
      uses enf:external-network-def {
        refine "internal-id" {
          default "secondary-wan";
          config false;
        }
        refine "sequence-number" {
          default "46";
          config false;
        }
        refine "resource-id" {
          config false;
        }
        refine "deploy-on" {
          config false;
        }
        refine "name" {
          default "secondary-wan";
        }
      }
      leaf level {
        type uint8;
        description
          "0..255";
        default "1";
        config false;
      }
      leaf secondary-wan-connectivity {
        type enumeration {
          enum "MPLS";
          enum "INET";
        }
        description
          "MPLS
           INET
          ";
        default "MPLS";
      }
    }
    container cpe-secondary-wan {
      uses ic:interconnect-def {
        refine "name" {
          default "cpe-secondary-wan";
          config false;
        }
        refine "deploy-on" {
          config false;
        }
        refine "resource-id" {
          config false;
        }
        refine "interconnect-name" {
          default "cpe-secondary-wan";
        }
        refine "sequence-number" {
          default "47";
          config false;
        }
        refine "internal-id" {
          config false;
        }
        refine "type" {
          config false;
        }
      }
      leaf endpoint1 {
        n-ext:end-point;
        type leafref {
          path "../../secondary-wan/internal-id";
        }
        description
          "Reference to the endpoint of the interconnect";
        default "secondary-wan";
        config false;
      }
      leaf endpoint2 {
        n-ext:end-point;
        type leafref {
          path "../../cpe/internal-id";
        }
        description
          "Reference to the endpoint of the interconnect";
        default "cpe";
        config false;
      }
      uses ic-local-props {
        refine "inbound-policy" {
          config false;
        }
        refine "cidr" {
          mandatory false;
          config false;
        }
        //refining as per cpe/ip-address
        refine "outbound-policy" {
          n-ext:maps-to "/ac:devices/ac:device[ac:id=current()/../../cpe/device-ip]/qos:policy-maps/policy-map/name";
        }
        refine "policy-name" {
          n-ext:maps-to "/ac:devices/ac:device[ac:id=current()/../../cpe/device-ip]/qos:policy-maps/policy-map/name";
        }
        refine "shape-average" {
          n-ext:maps-to "/ac:devices/ac:device[ac:id=current()/../../cpe/device-ip]/qos:policy-maps/policy-map[name=current()/../policy-name]/class-entry/shape-average";
        }
        refine "child-qos-policy" {
          n-ext:maps-to "/ac:devices/ac:device[ac:id=current()/../../cpe/device-ip]/qos:policy-maps/policy-map[name=current()/../policy-name]/class-entry/service-policy";
        }
        refine "speed" {
          n-ext:maps-to "/ac:devices/ac:device[ac:id=current()/../../cpe/device-ip]/if:interfaces/interface/link-speed";
        }
        refine "duplex" {
          n-ext:maps-to "/ac:devices/ac:device[ac:id=current()/../../cpe/device-ip]/if:interfaces/interface/duplex";
        }
        refine "in-queue-length" {
          n-ext:maps-to "/ac:devices/ac:device[ac:id=current()/../../cpe/device-ip]/if:interfaces/interface/in-queue-length";
        }
        refine "out-queue-length" {
          n-ext:maps-to "/ac:devices/ac:device[ac:id=current()/../../cpe/device-ip]/if:interfaces/interface/out-queue-length";
        }
      }
      list end-points {
        leaf sequence-number {
          type string;
          default "48";
          description
            "sequence-number";
          config false;
        }
        key "endpoint-name";
        uses end-point-props1;
        leaf endpoint-level-qos {
          type boolean;
          description
            "Check this option if you want to overwrite QoS policy specified in cpe-wan parent container";
          when "../interface-type = 'Physical' or ../interface-type = 'SVI' or ../interface-type = 'Sub-Interface'";
          default "false";
        }
        leaf inbound-qos-policy {
          type leafref {
            path "/ac:services/cpedeployment:managed-cpe-services/customer[name=current()/../../../../../name]/qos-service/policies/policy/name";
          }
          description
            "Select Inbound QoS Policy-Name";
          n-ext:maps-to "/ac:devices/ac:device[ac:id=current()/../device-ip]/if:interfaces/interface[long-name=current()/../interface-name]/inbound-qos";
          when "../endpoint-level-qos = 'true'";
        }
        leaf hierarchical-outbound-qos {
          type boolean;
          description
            "Check to configure a HQoS Outbound Policy";
          when "../endpoint-level-qos = 'true'";
        }
        leaf hierarchical-qos-policy-name {
          type string-no-lead-trail-space;
          description
            "Select the HQoS Outbound Policy Name";
          n-ext:maps-to "/ac:devices/ac:device[ac:id=current()/../device-ip]/if:interfaces/interface[long-name=current()/../interface-name]/outbound-qos";
          when "../endpoint-level-qos = 'true' and ../hierarchical-outbound-qos = 'true'";
        }
        leaf child-qos-policy-name {
          type leafref {
            path "/ac:services/cpedeployment:managed-cpe-services/customer[name=current()/../../../../../name]/qos-service/policies/policy/name";
          }
          description
            "Select Child QoS Policy-Name";
          n-ext:maps-to "/ac:devices/ac:device[ac:id=current()/../device-ip]/qos:policy-maps/policy-map[name=current()/../hierarchical-qos-policy-name]/class-entry/service-policy";
          when "../endpoint-level-qos = 'true' and ../hierarchical-outbound-qos = 'true'";
        }
        leaf shape-average {
          type uint64 {
            range "8000..10000000000";
          }
          description
            "Enter Shaping Average Bandwidth";
          when "../endpoint-level-qos = 'true' and ../hierarchical-outbound-qos = 'true'";
          n-ext:maps-to "/ac:devices/ac:device[ac:id=current()/../device-ip]/qos:policy-maps/policy-map[name=current()/../hierarchical-qos-policy-name]/class-entry/shape-average";
        }
        leaf bits-sustained {
          type uint64 {
            range "32..800000000";
          }
          description
            "Enter Shaper Bc Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-sustained";
        }
        leaf bits-excess {
          type uint64 {
            range "0..154400000";
          }
          description
            "Enter Shaper Be Value";
          when "../endpoint-level-qos = 'true' and ../hierarchical-outbound-qos = 'true'";
          n-ext:maps-to "/ac:devices/ac:device[ac:id=current()/../device-ip]/qos:policy-maps/policy-map[name=current()/../hierarchical-qos-policy-name]/class-entry/bits-excess";
        }
        leaf dmvpn-profile {
          type leafref {
            //path "../../../../../dmvpn-tunnel-profiles/dmvpn-tunnel-profile/name";
            path "/ac:services/cpedeployment:managed-cpe-services/customer[name=current()/../../../../../name]/dmvpn-tunnel-profiles/dmvpn-tunnel-profile/name";
          }
          description
            "Select DMVPN Profile";
          //n-ext:maps-to "/ac:devices/ac:device[ac:id=current()/../device-ip]/dmvpn:dmvpntunnels/dmvpntunnel/name";
          when "../interface-type = 'Tunnel'";
        }
        leaf p2p {
          type boolean;
          description
            "Check if P2P DMVPN Tunnel";
          when "../interface-type = 'Tunnel'";
        }
        leaf tunnel-interface-ip-address {
          type inet:ipv4-address;
          description
            "Enter Tunnel Interface IP Address";
          n-ext:maps-to "/ac:devices/ac:device[ac:id=current()/../device-ip]/dmvpn:dmvpntunnels/dmvpntunnel[name=current()/../tunnel-interface-id]/ipaddress";
          when "../interface-type = 'Tunnel'";
        }
        leaf tunnel-interface-mask {
          type inet:ipv4-address;
          description
            "Enter GRE Tunnel Interface Subnet Mask
             This is only required for non-DMVPN Tunnel Interface (eg: Zscaler)
            ";
          n-ext:maps-to "/ac:devices/ac:device[ac:id=current()/../device-ip]/dmvpn:dmvpntunnels/dmvpntunnel[name=current()/../tunnel-interface-id]/netmask";
          when "../interface-type = 'Tunnel'";
        }
        leaf tunnel-interface-destination {
          type inet:ipv4-address;
          description
            "Enter GRE Tunnel Destination
             This is only required for non-DMVPN Tunnel Interface (eg: Zscaler)
            ";
          n-ext:maps-to "/ac:devices/ac:device[ac:id=current()/../device-ip]/dmvpn:dmvpntunnels/dmvpntunnel[name=current()/../tunnel-interface-id]/tunnel-destination";
          when "../interface-type = 'Tunnel'";
        }
        leaf tunnel-interface-id {
          type uint32;
          description
            "Enter Tunnel Interface ID
             If this is a DMVPN Tunnel, this field will override the Tunnel ID from the DMPVPN Profile
            ";
          when "../interface-type = 'Tunnel'";
          n-ext:maps-to "/ac:devices/ac:device[ac:id=current()/../device-ip]/dmvpn:dmvpntunnels/dmvpntunnel/name";
        }
        leaf tunnel-source {
          type union {
            type string-no-lead-trail-space;
            type leafref {
              path "/ac:devices/ac:device[ac:id=current()/../device-ip]/if:interfaces/if:interface/if:name";
              require-instance false;
            }
          }
          description
            "Enter Tunnel Source Interface";
          n-ext:maps-to "/ac:devices/ac:device[ac:id=current()/../device-ip]/dmvpn:dmvpntunnels/dmvpntunnel[name=current()/../tunnel-interface-id]/tunnel-source";
          when "../interface-type = 'Tunnel'";
        }
        leaf tunnel-bandwidth {
          type uint32 {
            range "1..100000000";
          }
          description
            "Enter Tunnel Interface Bandwidth";
          units "Kbps";
          n-ext:maps-to "/ac:devices/ac:device[ac:id=current()/../device-ip]/dmvpn:dmvpntunnels/dmvpntunnel[name=current()/../tunnel-interface-id]/bandwidth";
          when "../interface-type = 'Tunnel'";
        }
        leaf tunnel-mss {
          type uint16;
          description
            "Enter GRE Tunnel Interface TCP MSS
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/tcp-adjust-mss";
        }
        leaf tunnel-mtu {
          type uint32;
          description
            "Enter GRE Tunnel Interface IP MTU
             This is only required for non-DMVPN Tunnel Interface (eg: Zscaler)
            ";
          when "../interface-type = 'Tunnel'";
          n-ext:maps-to "/ac:devices/ac:device[ac:id=current()/../device-ip]/dmvpn:dmvpntunnels/dmvpntunnel[name=current()/../tunnel-interface-id]/mtu";
        }
        list eigrp {
          leaf sequence-number {
            type string;
            default "49";
            description
              "sequence-number";
            config false;
          }
          key "name";
          uses eigrp-props-end;
        }
        list bgp-peers {
          leaf sequence-number {
            type string;
            default "50";
            description
              "sequence-number";
            config false;
          }
          key "BGP-peer-name";
          uses bgp-peer-props;
        }
      }
    }
    container lan {
      uses vnf:virtual-network-def {
        refine "internal-id" {
          default "lan";
          config false;
        }
        refine "sequence-number" {
          default "51";
          config false;
        }
        refine "resource-id" {
          config false;
        }
        refine "deploy-on" {
          config false;
        }
        refine "name" {
          default "lan";
        }
      }
      leaf level {
        type uint8;
        description
          "0..255";
        default "4";
        config false;
      }
      list switches {
        leaf sequence-number {
          type string;
          default "130";
          description
            "sequence-number";
          config false;
        }
        key "device";
        uses switch-def;
      }
    }
    container cpe-lan {
      uses ic:interconnect-def {
        refine "name" {
          default "cpe-lan";
          config false;
        }
        refine "deploy-on" {
          config false;
        }
        refine "resource-id" {
          config false;
        }
        refine "interconnect-name" {
          default "cpe-lan";
        }
        refine "sequence-number" {
          default "52";
          config false;
        }
        refine "internal-id" {
          config false;
        }
        refine "type" {
          config false;
        }
      }
      leaf endpoint1 {
        n-ext:end-point;
        type leafref {
          path "../../cpe/internal-id";
        }
        description
          "Reference to the endpoint of the interconnect";
        default "cpe";
        config false;
      }
      leaf endpoint2 {
        n-ext:end-point;
        type leafref {
          path "../../lan/internal-id";
        }
        description
          "Reference to the endpoint of the interconnect";
        default "lan";
        config false;
      }
      uses ic-local-props {
        refine "hierarchical-outbound-policy" {
          config false;
        }
        refine "outbound-policy" {
          config false;
        }
        refine "policy-name" {
          config false;
        }
        refine "shape-average" {
          config false;
        }
        refine "child-qos-policy" {
          config false;
        }
        refine "inbound-policy" {
          config false;
        }
        refine "cidr" {
          mandatory false;
          config false;
        }
        refine "auto-negotiation" {
          config false;
        }
        refine "speed" {
          config false;
        }
        refine "duplex" {
          config false;
        }
        refine "load-interval" {
          config false;
        }
        refine "hold-queue-in" {
          config false;
        }
        refine "hold-queue-out" {
          config false;
        }
      }
      list lan-profile {
        key "profile-name";
        leaf profile-name {
          type string;
          description
            "string";
        }
        uses ic-local {
          refine "cidr" {
            mandatory false;
          }
          refine "inbound-policy" {
            //n-ext:maps-to "/ac:devices/ac:device[ac:id=current()/../../cpe/device-ip]/qos:policy-maps/policy-map/name";
            n-ext:maps-to "/ac:devices/ac:device[ac:id=current()/../../../cpe/device-ip]/interface:interfaces/interface/inbound-qos";
          }
          refine "hierarchical-policy" {
            //n-ext:maps-to "/ac:devices/ac:device[ac:id=current()/../../cpe/device-ip]/qos:policy-maps/policy-map/name";
            n-ext:maps-to "/ac:devices/ac:device[ac:id=current()/../../../cpe/device-ip]/interface:interfaces/interface/inbound-qos";
          }
          refine "outbound-lan-policy" {
            //n-ext:maps-to "/ac:devices/ac:device[ac:id=current()/../../cpe/device-ip]/qos:policy-maps/policy-map/name";
            n-ext:maps-to "/ac:devices/ac:device[ac:id=current()/../../../cpe/device-ip]/interface:interfaces/interface/outbound-qos";
          }
          refine "hierarchical-egress-policy" {
            //n-ext:maps-to "/ac:devices/ac:device[ac:id=current()/../../cpe/device-ip]/qos:policy-maps/policy-map/name";
            n-ext:maps-to "/ac:devices/ac:device[ac:id=current()/../../../cpe/device-ip]/interface:interfaces/interface/outbound-qos";
          }
          refine "speed" {
            n-ext:maps-to "/ac:devices/ac:device[ac:id=current()/../../../cpe/device-ip]/if:interfaces/interface/link-speed";
          }
          refine "duplex" {
            n-ext:maps-to "/ac:devices/ac:device[ac:id=current()/../../../cpe/device-ip]/if:interfaces/interface/duplex";
          }
          refine "in-queue-length" {
            n-ext:maps-to "/ac:devices/ac:device[ac:id=current()/../../../cpe/device-ip]/if:interfaces/interface/in-queue-length";
          }
          refine "out-queue-length" {
            n-ext:maps-to "/ac:devices/ac:device[ac:id=current()/../../../cpe/device-ip]/if:interfaces/interface/out-queue-length";
          }
        }
      }
      list end-points {
        leaf sequence-number {
          type string;
          default "53";
          description
            "sequence-number";
          config false;
        }
        key "endpoint-name";
        leaf profile-name {
          type string;
          //type leafref {
          //  path "/ac:services/cpedeployment:managed-cpe-services/customer[name=current()/../../../../../name]/dual-cpe-site/dual-cpe-site-services[site-name=current()/../../../site-name]/cpe-lan/lan-profile/profile-name";
          //}
          description
            "string";
          //mandatory true;
        }
        uses end-point-props;
        list eigrp {
          leaf sequence-number {
            type string;
            default "54";
            description
              "sequence-number";
            config false;
          }
          key "name";
          uses eigrp-props-end;
        }
        list bgp-peers {
          leaf sequence-number {
            type string;
            default "55";
            description
              "sequence-number";
            config false;
          }
          key "BGP-peer-name";
          uses bgp-peer-props;
        }
      }
    }
    uses service-validations-def;
    uses failover-fallback-single-def;
  }

  grouping dc-def-dual {
    container single-cpe-dual-wan-site {
      list single-cpe-dual-wan-site-services {
        n-ext:ncx-service;
        key "site-name";
        leaf site-name {
          type string;
          description
            "string";
        }
        leaf bgp-as {
          type inet:as-number;
          description
            "Enter Site BGP AS Number";
          mandatory true;
          n-ext:maps-to "/ac:devices/ac:device[ac:id=current()/../cpe/device-ip]/l3:vrfs/vrf[name=GLOBAL]/router-bgp/as-number";
        }
        leaf zero-touch-prov {
          type boolean;
          description
            "Check if this is a Zero-Touch Provisioning";
        }
        leaf failover-state {
          type enumeration {
            enum "true";
            enum "false";
            enum "dps-off";
          }
          default "false";
          description
            "failover-state: True/False";
          config false;
        }
        leaf greenfield-site {
          type boolean;
          config false;
          description
            "greenfield-site: True/False";
        }
        leaf brownfield-site {
          type boolean;
          config false;
          description
            "brownfield-site: True/False";
        }
        leaf created-on {
          type string;
          description
            "string";
          config false;
        }
        leaf created-by {
          type string;
          description
            "string";
          config false;
        }
        leaf show-topology {
          type boolean;
          description
            "show-topology: True/False";
          config false;
          default "true";
        }
        uses dc-domain-dual-def;
        container policy-update-services {
          n-ext:ignore-for-brownfield;
          leaf sequence-number {
            type string;
            default "46";
            description
              "sequence-number";
            config false;
          }
          list cpe {
            key "end-point name";
            leaf end-point {
              type enumeration {
                enum "cpe-primary-wan";
                enum "cpe-secondary-wan";
              }
              description
                "cpe-primary-wan
                 cpe-secondary-wan
                ";
            }
            leaf name {
              type string;
              description
                "string";
            }
            leaf end-point1 {
              type leafref {
                path "../../../cpe-primary-wan/end-points/endpoint-name";
              }
              description
                "primary-wan-end-point";
              when " ../end-point = 'cpe-primary-wan' ";
            }
            leaf end-point2 {
              type leafref {
                path "../../../cpe-secondary-wan/end-points/endpoint-name";
              }
              description
                "secondary-wan-end-point";
              when " ../end-point = 'cpe-secondary-wan' ";
            }
            leaf sequence-number {
              type string;
              default "47";
              description
                "sequence-number";
              config false;
            }
            uses route-map-container-def;
          }
        }
      }
    }
  }

  grouping failover-fallback-single-def {
    container failover-fallback-service {
      list failover-fallback {
        key "transaction-id";
        leaf sequence-number {
          type string;
          default "89";
          description
            "sequence-number";
          config false;
        }
        leaf transaction-id {
          type string-no-space;
          description
            "Enter Transaction Name
             This is an internal field for Anuta NCX";
        }
        leaf operation-type {
          type enumeration {
            enum "failover";
            enum "fallback";
            enum "switch-off-dps";
            enum "switch-on-dps";
          }
          mandatory true;
          description
            "Select operation type:
             - Failover: Apply policy on all WAN eBGP peers configured under cpe-primary-wan
             - Fallback: Restore original policy on all WAN eBGP peers configured under cpe-primary-wan
             - Switch-Off-DPS: Apply CoPP policy to disable OSPF adjancecy on Tunnel100
             - Switch-On-DPS:  Remove CoPP policy to re-enable OSPF adjacency on Tunnel100";
        }
        leaf created-by {
          type string;
          description
            "string";
          config false;
        }
        leaf created-on {
          type string;
          description
            "string";
          config false;
        }
      }
    }
  }

  grouping dc-def {
    container single-cpe-site {
      list single-cpe-site-services {
        n-ext:ncx-service;
        key "site-name";
        leaf site-name {
          type string;
          description
            "Enter Site Name";
        }
        leaf bgp-as {
          type inet:as-number;
          description
            "Enter Site BGP AS Number";
          mandatory true;
          n-ext:maps-to "/ac:devices/ac:device[ac:id=current()/../cpe/device-ip]/l3:vrfs/vrf[name=GLOBAL]/router-bgp/as-number";
        }
        leaf zero-touch-prov {
          type boolean;
          description
            "Check if this is a Zero-Touch Provisioning Site";
        }
        leaf failover-state {
          type enumeration {
            enum "true";
            enum "false";
            enum "dps-off";
          }
          default "false";
          description
            "failover-state: True/False";
          config false;
        }
        leaf greenfield-site {
          type boolean;
          config false;
          description
            "greenfield-site: True/False";
        }
        leaf brownfield-site {
          type boolean;
          config false;
          description
            "brownfield-site: True/False";
        }
        leaf created-on {
          type string;
          description
            "string";
          config false;
        }
        leaf created-by {
          type string;
          description
            "string";
          config false;
        }
        leaf show-topology {
          type boolean;
          description
            "show-topology: True/False";
          config false;
          default "true";
        }
        uses dc-domain-def;
      }
    }
  }

  grouping domain-def {
    uses sm:service-def {
      refine "name" {
        mandatory true;
        description
          "Service name";
      }
      refine "service-sequence" {
        config false;
      }
      refine "resource-pool" {
        mandatory true;
      }
    }
    leaf total-sites {
      type string;
      description
        "string";
      config false;
    }
    leaf total-dps {
      type string;
      description
        "string";
      config false;
    }
    leaf single-cpe {
      type string;
      description
        "string";
      config false;
    }
    leaf single-cpe-dual {
      type string;
      description
        "string";
      config false;
    }
    leaf dual-cpe {
      type string;
      description
        "string";
      config false;
    }
    leaf dual-cpe-dual {
      type string;
      description
        "string";
      config false;
    }
    leaf triple-cpe {
      type string;
      description
        "string";
      config false;
    }
  }

  grouping dmvpn-tunnel-profile-def {
    container dmvpn-tunnel-profiles {
      //n-ext:ignore-for-brownfield;
      list dmvpn-tunnel-profile {
        key "name";
        uses dmvpn-domain-profile-def;
      }
      list update-dmvpn-tunnel-profile {
        n-ext:ignore-for-brownfield;
        key "id";
        leaf id {
          type string;
          description
            "string";
        }
        leaf tunnel-id {
          //type leafref {
          //path "/ac:services/cpedeployment:managed-cpe-services/customer[name=current()/../../../name]/dmvpn-tunnel-profiles/dmvpn-tunnel-profile/tunnel-id";
          //}
          type uint32;
          description
            "tunnel-id";
          mandatory true;
        }
        leaf update-profile {
          type boolean;
          description
            "Check to update customer template";
        }
        leaf operation {
          type operation-def;
          description
            "CREATE
             DELETE
            ";
        }
        leaf nhrp-nw-id {
          type uint32;
          description
            "NHRP Network Id and tunnel key can be same value";
          when " ../operation = 'CREATE' ";
          //n-ext:maps-to "/ac:devices/device/dmvpn:dmvpntunnels/dmvpntunnel/nhrp-network-id";
        }
        leaf tunnel-key {
          type uint32;
          description
            "Tunnel key and NHRP Network Id can be same value";
          when " ../operation = 'CREATE' ";
          //n-ext:maps-to "/ac:devices/device/dmvpn:dmvpntunnels/dmvpntunnel/tunnel-key";
        }
        leaf nhrp-holdtime {
          type uint32 {
            range "1..65535";
          }
          description
            "NHRP Holdtime";
          when " ../operation = 'CREATE' ";
        }
        leaf nhrp-authentication-key {
          type string-no-space {
            length "1..8";
          }
          description
            "NHRP authentication key";
          when " ../operation = 'CREATE' ";
          //n-ext:maps-to "/ac:devices/device/dmvpn:dmvpntunnels/dmvpntunnel/nhrp-auth-key";
        }
        leaf wan-tunnel-ip {
          type inet:ip-address;
          description
            "NHRP Map Tunnel IP Address";
          //n-ext:maps-to "/ac:devices/device/dmvpn:dmvpntunnels/dmvpntunnel/nhrp-maps/sourceip";
        }
        leaf wan-public-ip {
          type inet:ip-address;
          description
            "NHRP Map NBMA Address";
          //n-ext:maps-to "/ac:devices/device/dmvpn:dmvpntunnels/dmvpntunnel/nhrp-maps/destip";
        }
        leaf mtu {
          type uint32;
          description
            "Tunnel Interface IP MTU";
          when " ../operation = 'CREATE' ";
          //n-ext:maps-to "/ac:devices/device/dmvpn:dmvpntunnels/dmvpntunnel/mtu";
        }
        leaf tcp-adjust-mss {
          type uint32;
          description
            "0..4294967295";
          when " ../operation = 'CREATE' ";
          //n-ext:maps-to "/ac:devices/device/dmvpn:dmvpntunnels/dmvpntunnel/tcp-adjust-mss";
        }
        leaf tunnel-bandwidth {
          type uint32 {
            range "1..100000000";
          }
          description
            "Enter Tunnel Interface Bandwidth";
          when " ../operation = 'CREATE' ";
          //n-ext:maps-to "/ac:devices/device/dmvpn:dmvpntunnels/dmvpntunnel[name=current()/../name]/bandwidth";
        }
        leaf fvrf {
          type leafref {
            path "/ac:services/cpedeployment:managed-cpe-services/customer[name=current()/../../../name]/vrfs/vrf/vrf-name";
          }
          description
            "fvrf";
          when " ../operation = 'CREATE' ";
          //n-ext:maps-to "/ac:devices/device/dmvpn:dmvpntunnels/dmvpntunnel/front-vrf-name";
        }
        leaf ipsec-profile {
          type leafref {
            path "/ac:services/cpedeployment:managed-cpe-services/customer[name=current()/../../../name]/ipsec/ipsec-profiles/ipsec-profile/ipsec-profile-name";
          }
          description
            "ipsec-profile";
          when " ../operation = 'CREATE' ";
          //n-ext:maps-to "/ac:devices/device/dmvpn:dmvpntunnels/dmvpntunnel/ipsec-profile-name";
        }
        leaf apply-to-sites {
          type boolean;
          description
            "Check if you want to perform bulk update operation on individual sites";
          when "../apply-to-device-group = 'false'";
        }
        leaf apply-to-device-group {
          type boolean;
          description
            "Check if you want to perform bulk update operation on device group";
          when "../apply-to-sites = 'false'";
        }
        leaf device-group {
          type leafref {
            path "/ac:data-grouping/ac:definition/ac:name";
          }
          description
            "device-group";
          when "../apply-to-device-group = 'true'";
        }
        leaf single-cpe-site {
          type boolean;
          description
            "single-cpe-site: True/False";
          when "../apply-to-sites = 'true'";
        }
        leaf-list single-cpe-sites {
          type leafref {
            path "../../../single-cpe-site/single-cpe-site-services/site-name";
            require-instance false;
          }
          description
            "single-sites";
          when " ../single-cpe-site = 'true' ";
        }
        leaf dual-cpe-site {
          type boolean;
          description
            "dual-cpe-site: True/False";
          when "../apply-to-sites = 'true'";
        }
        leaf-list dual-cpe-sites {
          type leafref {
            path "../../../dual-cpe-site/dual-cpe-site-services/site-name";
            require-instance false;
          }
          description
            "dual-sites";
          when " ../dual-cpe-site = 'true' ";
        }
        leaf single-cpe-dual-wan-site {
          type boolean;
          description
            "single-cpe-dual-wan-site: True/False";
          when "../apply-to-sites = 'true'";
        }
        leaf-list single-cpe-dual-wan-sites {
          type leafref {
            path "../../../single-cpe-dual-wan-site/single-cpe-dual-wan-site-services/site-name";
            require-instance false;
          }
          description
            "single-sites";
          when " ../single-cpe-dual-wan-site = 'true' ";
        }
        leaf dual-cpe-dual-wan-site {
          type boolean;
          description
            "dual-cpe-dual-wan-site: True/False";
          when "../apply-to-sites = 'true'";
        }
        leaf-list dual-cpe-dual-wan-sites {
          type leafref {
            path "../../../dual-cpe-dual-wan-site/dual-cpe-dual-wan-site-services/site-name";
            require-instance false;
          }
          description
            "dual-sites";
          when " ../dual-cpe-dual-wan-site = 'true' ";
        }
        leaf triple-cpe-site {
          type boolean;
          description
            "triple-cpe-site: True/False";
          when "../apply-to-sites = 'true'";
        }
        leaf-list triple-cpe-sites {
          type leafref {
            path "../../../triple-cpe-site/triple-cpe-site-services/site-name";
            require-instance false;
          }
          description
            "single-sites";
          when " ../triple-cpe-site = 'true' ";
        }
      }
    }
  }

  grouping dmvpn-domain-profile-def {
    leaf name {
      type string-no-space;
      description
        "name";
      n-ext:maps-to "/ac:devices/device/dmvpn:dmvpntunnels/dmvpntunnel/name";
    }
    leaf tunnel-prefix {
      type leafref {
        path "/ip:ipaddress-pools/ip:ipaddress-pool/ip:name";
      }
      n-ext-ui:ncx-ext-pagination "paginate";
      description
        "Tunnel subnet";
      //mandatory true;
    }
    leaf nhrp-nw-id {
      type uint32;
      description
        "NHRP Network Id and tunnel key can be same value";
      n-ext:maps-to "/ac:devices/ac:device/dmvpn:dmvpntunnels/dmvpntunnel[name=current()/../name]/nhrp-network-id";
    }
    leaf tunnel-key {
      type uint32;
      description
        "Tunnel key and NHRP Network Id can be same value";
      mandatory true;
      n-ext:maps-to "/ac:devices/ac:device/dmvpn:dmvpntunnels/dmvpntunnel[name=current()/../name]/tunnel-key";
    }
    leaf tunnel-id {
      type uint16;
      description
        "Tunnel interface id";
      mandatory true;
      n-ext:maps-to "/ac:devices/ac:device/dmvpn:dmvpntunnels/dmvpntunnel[name=current()/../name]/name";
    }
    leaf nhrp-authentication-key {
      type string {
        length "1..8";
      }
      description
        "NHRP authentication key";
      mandatory true;
      n-ext:maps-to "/ac:devices/ac:device/dmvpn:dmvpntunnels/dmvpntunnel[name=current()/../name]/nhrp-auth-key";
    }
    leaf wan-tunnel-ip {
      type inet:ip-address;
      description
        "DC router tunnel IP address from tunnel prefix range";
      //mandatory true;
      n-ext:maps-to "/ac:devices/ac:device/dmvpn:dmvpntunnels/dmvpntunnel[name=current()/../name]/nhrp-maps/sourceip";
    }
    leaf wan-public-ip {
      type inet:ip-address;
      description
        "DC router tunnel source interface IP address";
      //mandatory true;
      n-ext:maps-to "/ac:devices/ac:device/dmvpn:dmvpntunnels/dmvpntunnel[name=current()/../name]/nhrp-maps/destip";
    }
    leaf mtu {
      type uint32;
      description
        "0..4294967295";
      default "1400";
      n-ext:maps-to "/ac:devices/ac:device/dmvpn:dmvpntunnels/dmvpntunnel[name=current()/../name]/mtu";
    }
    leaf tcp-adjust-mss {
      type uint32;
      description
        "0..4294967295";
      default "1360";
      n-ext:maps-to "/ac:devices/ac:device/dmvpn:dmvpntunnels/dmvpntunnel[name=current()/../name]/tcp-adjust-mss";
    }
    leaf ipsec-profile {
      type leafref {
        path "../../../ipsec/ipsec-profiles/ipsec-profile/ipsec-profile-name";
      }
      description
        "ipsec-profile";
      n-ext:maps-to "/ac:devices/ac:device/dmvpn:dmvpntunnels/dmvpntunnel[name=current()/../name]/ipsec-profile-name";
    }
    leaf no-nhrp-route-watch {
      type boolean;
      description
        "no-nhrp-route-watch: True/False";
      n-ext:maps-to "/ac:devices/ac:device/dmvpn:dmvpntunnels/dmvpntunnel[name=current()/../name]/no-nhrp-route-watch";
    }
    leaf nhrp-reg-no-uniq {
      type boolean;
      description
        "nhrp-reg-no-uniq: True/False";
      n-ext:maps-to "/ac:devices/ac:device/dmvpn:dmvpntunnels/dmvpntunnel[name=current()/../name]/nhrp-reg-no-uniq";
    }
    leaf nhrp-reg-timeout {
      type uint32;
      description
        "0..4294967295";
      n-ext:maps-to "/ac:devices/ac:device/dmvpn:dmvpntunnels/dmvpntunnel[name=current()/../name]/nhrp-reg-timeout";
    }
    leaf nhrp-holdtime {
      type uint16 {
        range "1..65535";
      }
      description
        "1..65535";
      default "3600";
      n-ext:maps-to "/ac:devices/ac:device/dmvpn:dmvpntunnels/dmvpntunnel[name=current()/../name]/nhrp-holdtime";
    }
    leaf nhrp-redirect {
      type boolean;
      description
        "nhrp-redirect: True/False";
      n-ext:maps-to "/ac:devices/ac:device/dmvpn:dmvpntunnels/dmvpntunnel[name=current()/../name]/nhrp-redirect";
    }
    leaf nhrp-shortcut {
      type boolean;
      description
        "nhrp-shortcut: True/False";
      n-ext:maps-to "/ac:devices/ac:device/dmvpn:dmvpntunnels/dmvpntunnel[name=current()/../name]/nhrp-shortcut";
    }
    leaf if-state-nhrp {
      type boolean;
      description
        "if-state-nhrp: True/False";
      n-ext:maps-to "/ac:devices/ac:device/dmvpn:dmvpntunnels/dmvpntunnel[name=current()/../name]/if-state-nhrp";
    }
    leaf tunnel-keepalive-period {
      type uint16 {
        range "0..32767";
      }
      description
        "0..32767";
      n-ext:maps-to "/ac:devices/ac:device/dmvpn:dmvpntunnels/dmvpntunnel[name=current()/../name]/tunnel-keepalive-period";
    }
    leaf tunnel-keepalive-retries {
      type uint8 {
        range "1..255";
      }
      description
        "1..255";
      n-ext:maps-to "/ac:devices/ac:device/dmvpn:dmvpntunnels/dmvpntunnel[name=current()/../name]/tunnel-keepalive-retries";
    }
    leaf delay {
      type uint32;
      description
        "0..4294967295";
      //default "100";
      n-ext:maps-to "/ac:devices/ac:device/dmvpn:dmvpntunnels/dmvpntunnel[name=current()/../name]/delay";
    }
    list nhrp-maps {
      key "wan-tunnel-ip wan-public-ip";
      uses nhrp-map;
    }
  }

  grouping nhrp-map {
    leaf wan-tunnel-ip {
      type inet:ip-address;
      description
        "Valid IPv4/v6 Address (A.B.C.D for e.x: 172.16.1.1 or X::Y for e.x: 2001::1)";
      //n-ext:maps-to "/ac:devices/device/dmvpn:dmvpntunnels/dmvpntunnel[name=current()/../name]/delay";
      n-ext:maps-to "/ac:devices/ac:device/dmvpn:dmvpntunnels/dmvpntunnel[name=current()/../../name]/nhrp-maps/sourceip";
    }
    leaf wan-public-ip {
      type inet:ip-address;
      description
        "Valid IPv4/v6 Address (A.B.C.D for e.x: 172.16.1.1 or X::Y for e.x: 2001::1)";
      n-ext:maps-to "/ac:devices/ac:device/dmvpn:dmvpntunnels/dmvpntunnel[name=current()/../../name]/nhrp-maps/destip";
    }
  }

  grouping ipsec-def {
    container ipsec {
      //n-ext:ignore-for-brownfield;
      container crypto-profiles {
        list crypto-profile {
          key "crypto-profile-name";
          uses crypto-profile-def;
        }
      }
      container transform-sets {
        list transform-set {
          key "transform-set-name";
          uses transform-set;
        }
      }
      container ipsec-profiles {
        list ipsec-profile {
          key "ipsec-profile-name";
          uses ipsec-profile;
        }
      }
      list delete-ipsec-profile {
        n-ext:ignore-for-brownfield;
        key "id";
        leaf id {
          type string;
          description
            "string";
        }
        leaf ipsec-profile-name {
          type leafref {
            path "/ac:services/cpedeployment:managed-cpe-services/customer[name=current()/../../../name]/ipsec/ipsec-profiles/ipsec-profile/ipsec-profile-name";
          }
          description
            "ipsec-profile-name";
          n-ext:maps-to "/ac:devices/ac:device/dmvpn:ipsec-profiles/ipsec-profile/ipsec-profile-name";
        }
        leaf single-cpe-site {
          type boolean;
          description
            "single-cpe-site: True/False";
        }
        leaf-list single-cpe-sites {
          type leafref {
            path "../../../single-cpe-site/single-cpe-site-services/site-name";
            require-instance false;
          }
          description
            "single-sites";
          when " ../single-cpe-site = 'true' ";
        }
        leaf dual-cpe-site {
          type boolean;
          description
            "dual-cpe-site: True/False";
        }
        leaf-list dual-cpe-sites {
          type leafref {
            path "../../../dual-cpe-site/dual-cpe-site-services/site-name";
            require-instance false;
          }
          description
            "dual-sites";
          when " ../dual-cpe-site = 'true' ";
        }
        leaf single-cpe-dual-wan-site {
          type boolean;
          description
            "single-cpe-dual-wan-site: True/False";
        }
        leaf-list single-cpe-dual-wan-sites {
          type leafref {
            path "../../../single-cpe-dual-wan-site/single-cpe-dual-wan-site-services/site-name";
            require-instance false;
          }
          description
            "single-sites";
          when " ../single-cpe-dual-wan-site = 'true' ";
        }
        leaf dual-cpe-dual-wan-site {
          type boolean;
          description
            "dual-cpe-dual-wan-site: True/False";
        }
        leaf-list dual-cpe-dual-wan-sites {
          type leafref {
            path "../../../dual-cpe-dual-wan-site/dual-cpe-dual-wan-site-services/site-name";
            require-instance false;
          }
          description
            "dual-sites";
          when " ../dual-cpe-dual-wan-site = 'true' ";
        }
        leaf triple-cpe-site {
          type boolean;
          description
            "triple-cpe-site: True/False";
        }
        leaf-list triple-cpe-sites {
          type leafref {
            path "../../../triple-cpe-site/triple-cpe-site-services/site-name";
            require-instance false;
          }
          description
            "single-sites";
          when " ../triple-cpe-site = 'true' ";
        }
      }
    }
  }

  grouping crypto-profile-def {
    leaf crypto-profile-name {
      type string;
      description
        "string";
      n-ext:maps-to "/ac:devices/ac:device/dmvpn:crypto/crypto-profile/ike-profile-name";
    }
    leaf crypto-type {
      type crypto-version;
      description
        "IKEV1
         IKEV2
        ";
      default "IKEV1";
      n-ext:maps-to "/ac:devices/ac:device/dmvpn:crypto/crypto-profile[crypto-profile-name=current()/../crypto-profile-name]/ike-version";
    }
    leaf keyring {
      type string-no-space;
      description
        "string";
      n-ext:maps-to "/ac:devices/ac:device/dmvpn:crypto/crypto-profile[crypto-profile-name=current()/../crypto-profile-name]/key-ring-name";
    }
    leaf allow-all {
      type boolean;
      description
        "allow-all: True/False";
    }
    leaf pre-shared-key {
      type string;
      description
        "string";
      mandatory true;
      n-ext:maps-to "/ac:devices/ac:device/dmvpn:crypto-keyrings/crypto-keyring[key-ring-name=current()/../keyring]/pre-shared-key/pre-shared-secret";
    }
    leaf vrf {
      type string-no-space;
      description
        "string";
      //n-ext:maps-to "/ac:devices/device/dmvpn:crypto/crypto-profile[crypto-profile-name=current()/../crypto-profile-name]/match/vrf-name";
      n-ext:maps-to "/ac:devices/ac:device/dmvpn:crypto-keyrings/crypto-keyring[key-ring-name=current()/../keyring]/vrf-name";
    }
    leaf encryption {
      type encryption;
      description
        "DES
         3DES
         AES128
         AES192
         AES256
         esp-aes
        ";
      n-ext:maps-to "/ac:devices/ac:device/dmvpn:crypto-policies/crypto-policy[policy-number=current()/../policy-number]/ike-encryption-type";
    }
    leaf authentication {
      type authentication;
      description
        "MD5
         SHA1
         SHA256
         SHA384
         SHA512
         esp-sha-hmac
        ";
      //      n-ext:maps-to "/ac:devices/device/dmvpn:crypto/hash";
      n-ext:maps-to "/ac:devices/ac:device/dmvpn:crypto-policies/crypto-policy[policy-number=current()/../policy-number]/hash";
    }
    leaf policy-number {
      type uint32;
      description
        "0..4294967295";
      when " ../crypto-type = 'IKEV1' ";
      n-ext:maps-to "/ac:devices/ac:device/dmvpn:crypto-policies/crypto-policy[crypto-type=IKEV1]/policy-number";
    }
    leaf local-address {
      type string-no-space;
      description
        "Enter Crypto ISAKMP Profile Source Interface";
    }
    leaf auth-type {
      type auth-mode;
      description
        "pre-share
         rsa-sig
        ";
      when " ../crypto-type = 'IKEV1' ";
      //n-ext:maps-to "/ac:devices/device/dmvpn:crypto/crypto-profile/auth-type";
      n-ext:maps-to "/ac:devices/ac:device/dmvpn:crypto-policies/crypto-policy[policy-number=current()/../policy-number]/auth-type";
    }
    leaf group {
      type uint32;
      description
        "0..4294967295";
      when " ../crypto-type = 'IKEV1' ";
      n-ext:maps-to "/ac:devices/ac:device/dmvpn:crypto-policies/crypto-policy[policy-number=current()/../policy-number]/group";
    }
    leaf life-time {
      type uint32;
      description
        "0..4294967295";
      when " ../crypto-type = 'IKEV1' ";
      //n-ext:maps-to "/ac:devices/device/dmvpn:crypto/crypto-profile/life-time";
      n-ext:maps-to "/ac:devices/ac:device/dmvpn:crypto-policies/crypto-policy[policy-number=current()/../policy-number]/life-time";
    }
    leaf keepalive {
      type uint16 {
        range "10..3600";
      }
      description
        "Enter ISAKMP keepalive timer in seconds";
      when " ../crypto-type = 'IKEV1' ";
    }
  }

  grouping transform-set {
    leaf transform-set-name {
      type string;
      description
        "string";
      //n-ext:maps-to "/ac:devices/device/dmvpn:crypto/transform-set";
      n-ext:maps-to "/ac:devices/ac:device/dmvpn:transform-sets/transform-set/transform-set";
    }
    leaf mode {
      type ipsec-mode;
      description
        "transport
         tunnel
        ";
      default "transport";
      n-ext:maps-to "/ac:devices/ac:device/dmvpn:transform-sets/transform-set[transform-set=current()/../transform-set-name]/mode";
    }
    leaf encryption {
      type encryption_transform;
      description
        "esp-aes
         esp-3des
         esp-des
         esp-aes 128
         esp-aes 192
         esp-aes 256
        ";
      //      n-ext:maps-to "/ac:devices/device/dmvpn:crypto/ipsec-encryption-type";
      n-ext:maps-to "/ac:devices/ac:device/dmvpn:transform-sets/transform-set[transform-set=current()/../transform-set-name]/ipsec-encryption-type";
    }
    leaf authentication {
      type authentication_transform;
      description
        "esp-md5-hmac
         esp-sha-hmac
         esp-sha256-hmac
         esp-sha384-hmac
         esp-sha512-hmac
        ";
      //      n-ext:maps-to "/ac:devices/device/dmvpn:crypto/ipsec-authentication-type";
      n-ext:maps-to "/ac:devices/ac:device/dmvpn:transform-sets/transform-set[transform-set=current()/../transform-set-name]/ipsec-authentication-type";
    }
  }

  grouping ipsec-profile {
    leaf ipsec-profile-name {
      type string;
      description
        "string";
      n-ext:maps-to "/ac:devices/ac:device/dmvpn:ipsec-profiles/ipsec-profile/ipsec-profile-name";
    }
    leaf sa-lifetime {
      type uint32;
      description
        "IPSec SA lifetime";
      n-ext:maps-to "/ac:devices/ac:device/dmvpn:ipsec-profiles/ipsec-profile[ipsec-profile-name=current()/../ipsec-profile-name]/life-time";
    }
    leaf transform-set {
      type leafref {
        path "../../../../ipsec/transform-sets/transform-set/transform-set-name";
      }
      description
        "transform-set";
      mandatory true;
      n-ext:maps-to "/ac:devices/ac:device/dmvpn:ipsec-profiles/ipsec-profile[ipsec-profile-name=current()/../ipsec-profile-name]/transform-set";
    }
    leaf crypto-profile {
      type leafref {
        path "../../../../ipsec/crypto-profiles/crypto-profile/crypto-profile-name";
      }
      description
        "crypto-profile";
      mandatory true;
      n-ext:maps-to "/ac:devices/ac:device/dmvpn:ipsec-profiles/ipsec-profile[ipsec-profile-name=current()/../ipsec-profile-name]/ike-profile-name";
    }
    leaf shared {
      type boolean;
      description
        "shared: True/False";
      n-ext:maps-to "/ac:devices/ac:device/dmvpn:ipsec-profiles/ipsec-profile[ipsec-profile-name=current()/../ipsec-profile-name]/shared";
    }
  }

  grouping prefix-lists-def {
    container prefix-lists {
      //n-ext:ignore-for-brownfield;
      list prefix-list {
        key "prefix-list-name";
        uses prefix-list-def;
      }
      list update-prefix-list {
        n-ext:ignore-for-brownfield;
        key "id";
        leaf id {
          type string-no-space;
          description
            "Enter Prefix-List Bulk Update Transaction ID
             This is an internal field for Anuta NCX";
        }
        leaf prefix-list-name {
          type leafref {
            path "/ac:services/cpedeployment:managed-cpe-services/customer[name=current()/../../../name]/prefix-lists/prefix-list/prefix-list-name";
          }
          description
            "Select Prefix-List Name";
          mandatory true;
          //n-ext:maps-to "/ac:devices/device/l3features:ip-prefixlist-list/ip-prefixlist/name";
        }
        leaf operation {
          type operation-def;
          description
            "CREATE
             DELETE
            ";
        }
        leaf update-profile {
          type boolean;
          description
            "Check to update customer template";
        }
        leaf prefix-name {
          type string;
          description
            "string";
          when " ../operation = 'CREATE' ";
          //n-ext:maps-to "/ac:devices/device/l3features:ip-prefixlist-list/ip-prefixlist[name=current()/../prefix-list-name]/ip-prefixlist-entries/ip-prefixlist-entry[rule-num=current()/../rule-num]/prefix-name";
        }
        leaf rule-num {
          type uint32 {
            range "1..4294967294";
          }
          //type leafref {
          //  path "/ac:services/cpedeployment:managed-cpe-services/customer[name=current()/../../../name]/prefix-lists/prefix-list[prefix-list-name=current()/../prefix-list-name]/prefix/rule-num";
          //}
          description
            "Enter Prefix-List entry sequence number";
          mandatory true;
          //n-ext:maps-to "/ac:devices/device/l3features:ip-prefixlist-list/ip-prefixlist[name=current()/../prefix-list-name]/ip-prefixlist-entries/ip-prefixlist-entry/rule-num";
        }
        leaf ipv4-prefix {
          type inet:ipv4-prefix;
          description
            "Enter IPv4 Prefix (eg: 10.0.0.0/24)";
          when " ../operation = 'CREATE' ";
        }
        leaf condition {
          type enumeration {
            enum "permit";
            enum "deny";
          }
          description
            "Select Prefix-List entry condition";
          when " ../operation = 'CREATE' ";
        }
        leaf exact-matching-prefix-length {
          type matching-prefix-type;
          description
            "string";
          when " ../operation = 'CREATE' ";
        }
        leaf minimum-matching-prefix-length {
          type matching-prefix-type;
          description
            "Enter minimum subnet length to match";
          when " ../operation = 'CREATE' ";
        }
        leaf maximum-matching-prefix-length {
          type matching-prefix-type;
          description
            "Enter maximum subnet length to match";
          when " ../operation = 'CREATE' ";
        }
        leaf apply-to-sites {
          type boolean;
          description
            "Check if you want to perform bulk update operation on individual sites";
          when "../apply-to-device-group = 'false'";
        }
        leaf apply-to-device-group {
          type boolean;
          description
            "Check if you want to perform bulk update operation on device group";
          when "../apply-to-sites = 'false'";
        }
        leaf device-group {
          type leafref {
            path "/ac:data-grouping/ac:definition/ac:name";
          }
          description
            "device-group";
          when "../apply-to-device-group = 'true'";
        }
        leaf single-cpe-site {
          type boolean;
          description
            "single-cpe-site: True/False";
          when "../apply-to-sites = 'true'";
        }
        leaf-list single-cpe-sites {
          type leafref {
            path "../../../single-cpe-site/single-cpe-site-services/site-name";
            require-instance false;
          }
          description
            "single-sites";
          when " ../single-cpe-site = 'true' ";
        }
        leaf dual-cpe-site {
          type boolean;
          description
            "dual-cpe-site: True/False";
          when "../apply-to-sites = 'true'";
        }
        leaf-list dual-cpe-sites {
          type leafref {
            path "../../../dual-cpe-site/dual-cpe-site-services/site-name";
            require-instance false;
          }
          description
            "dual-sites";
          when " ../dual-cpe-site = 'true' ";
        }
        leaf single-cpe-dual-wan-site {
          type boolean;
          description
            "single-cpe-dual-wan-site: True/False";
          when "../apply-to-sites = 'true'";
        }
        leaf-list single-cpe-dual-wan-sites {
          type leafref {
            path "../../../single-cpe-dual-wan-site/single-cpe-dual-wan-site-services/site-name";
            require-instance false;
          }
          description
            "single-sites";
          when " ../single-cpe-dual-wan-site = 'true' ";
        }
        leaf dual-cpe-dual-wan-site {
          type boolean;
          description
            "dual-cpe-dual-wan-site: True/False";
          when "../apply-to-sites = 'true'";
        }
        leaf-list dual-cpe-dual-wan-sites {
          type leafref {
            path "../../../dual-cpe-dual-wan-site/dual-cpe-dual-wan-site-services/site-name";
            require-instance false;
          }
          description
            "dual-sites";
          when " ../dual-cpe-dual-wan-site = 'true' ";
        }
        leaf triple-cpe-site {
          type boolean;
          description
            "triple-cpe-site: True/False";
          when "../apply-to-sites = 'true'";
        }
        leaf-list triple-cpe-sites {
          type leafref {
            path "../../../triple-cpe-site/triple-cpe-site-services/site-name";
            require-instance false;
          }
          description
            "single-sites";
          when " ../triple-cpe-site = 'true' ";
        }
      }
    }
  }

  grouping route-map-container-def {
    leaf import-route-map {
      type leafref {
        //path "../../../../../route-maps/route-map/route-map-name";
        path "/ac:services/cpedeployment:managed-cpe-services/customer[name=current()/../../../../../name]/route-maps/route-map/route-map-name";
      }
      description
        "import-route-map";
    }
    leaf export-route-map {
      type leafref {
        //path "../../../../../route-maps/route-map/route-map-name";
        path "/ac:services/cpedeployment:managed-cpe-services/customer[name=current()/../../../../../name]/route-maps/route-map/route-map-name";
      }
      description
        "export-route-map";
    }
  }

  grouping associated-service-def {
    container policy-update-services {
      n-ext:ignore-for-brownfield;
      leaf sequence-number {
        type string;
        default "63";
        description
          "sequence-number";
        config false;
      }
      leaf rtt-trigger {
        type string;
        default "false";
        description
          "naas event trap flag";
      }
      list cpe-primary {
        key "end-point";
        leaf end-point {
          type leafref {
            path "../../../cpe-primary-wan/end-points/endpoint-name";
          }
          description
            "primary-ic-end-point";
        }
        leaf sequence-number {
          type string;
          default "64";
          description
            "sequence-number";
          config false;
        }
        uses route-map-container-def;
      }
      list cpe-secondary {
        key "end-point";
        leaf end-point {
          type leafref {
            path "../../../cpe-secondary-wan/end-points/endpoint-name";
          }
          description
            "secondary-ic-end-point";
        }
        leaf sequence-number {
          type string;
          default "65";
          description
            "sequence-number";
          config false;
        }
        uses route-map-container-def;
      }
      container hsrp-update-service {
        n-ext:ignore-for-brownfield;
        leaf sequence-number {
          type string;
          default "66";
          description
            "sequence-number";
          config false;
        }
        leaf cpe-primary-hsrp-priority {
          type uint16 {
            range "0..255";
          }
          description
            "0..255";
        }
        leaf cpe-secondary-hsrp-priority {
          type uint16 {
            range "0..255";
          }
          description
            "0..255";
        }
      }
    }
  }

  grouping acl-def {
    leaf name {
      type string-no-space;
      n-ext:maps-to "/ac:devices/ac:device/acl:access-lists/access-list/name";
      /*type leafref {
               path "/ac:devices/ac:device[ac:id=/rp:resource-pools/rp:resource-pool[rp:name=current()/../../../resource-pool]/rp:device/rp:id]/acl:access-lists/access-list/name";
               //path "/rp:resource-pools/rp:resource-pool[rp:name=current()/../../resource-pool]/rp:device/rp:id";
             }
      <n-ext-ui:ncx-ext-allowed-vals path="/rp:resource-pools/rp:resource-pool[rp:name=current()/../../../resource-pool]/rp:device/rp:id"/>*/
      description
        "Enter ACL Name";
    }
    leaf access-list-entry {
      type access-list-entry-type;
      description
        "Enter ACL Type (Standard/Extended)\n";
      default "extended";
      n-ext:maps-to "/ac:devices/ac:device/acl:access-lists/access-list[name=current()/../name]/acl-type";
      //n-ext:maps-to "/ac:devices/device/acl:access-lists/access-list/acl-type";
    }
    leaf sequence-number {
      type string;
      default "13";
      description
        "sequence-number";
      config false;
    }
    leaf dps {
      type boolean;
      description
        "Check if this an ACL use for DPS traffic classification";
    }
    list access-list-rules {
      key "name action";
      leaf name {
        type string-no-lead-trail-space;
        n-ext:maps-to "/ac:devices/ac:device/acl:access-lists/access-list[name=current()/../../name]/acl-rules/acl-rule/name";
        //n-ext:maps-to "/ac:devices/device/acl:access-lists/access-list/acl-rules/acl-rule/name";
        description
          "Enter ACL Rule Name
           This is an internal field used by Anuta NCX
          ";
      }
      leaf acl-sequence-num {
        type uint32 {
          range "1..2147483647";
        }
        description
          "Enter ACL Rule Sequence Number";
        n-ext:maps-to "/ac:devices/ac:device/acl:access-lists/access-list[name=current()/../../name]/acl-rules/acl-rule[name=current()/../name]/linenumber";
      }
      leaf action {
        type enumeration {
          enum "permit";
          enum "deny";
        }
        //type leafref {
        //path="/ac:devices/ac:device/acl:access-lists/access-list[name=current()/../../name]/acl-rules/acl-rule[name=current()/../name]/action";
        //}
        n-ext:maps-to "/ac:devices/ac:device/acl:access-lists/access-list[name=current()/../../name]/acl-rules/acl-rule[name=current()/../name]/action";
        //n-ext:maps-to "/ac:devices/device/acl:access-lists/access-list/acl-rules/acl-rule/action";
        description
          "Enter ACL Rule Action (Permit/Deny)\n";
      }
      leaf protocol {
        type enumeration {
          enum "ahp";
          enum "eigrp";
          enum "esp";
          enum "gre";
          enum "icmp";
          enum "igmp";
          enum "ip";
          enum "ipinip";
          enum "object-group";
          enum "ospf";
          enum "pcp";
          enum "pim";
          enum "tcp";
          enum "udp";
        }
        n-ext:maps-to "/ac:devices/ac:device/acl:access-lists/access-list[name=current()/../../name]/acl-rules/acl-rule[name=current()/../name]/layer4protocol";
        //n-ext:maps-to "/ac:devices/device/acl:access-lists/access-list/acl-rules/acl-rule/layer4protocol";
        description
          "Enter ACL Extended Rule Protocol (tcp/udp/ip/gre/...)\n";
      }
      leaf service-obj-name {
        type leafref {
          path "/ac:services/cpedeployment:managed-cpe-services/customer[name=current()/../../../../name]/object-groups/object-group/name";
        }
        n-ext:maps-to "/ac:devices/ac:device/acl:access-lists/access-list[name=current()/../../name]/acl-rules/acl-rule[name=current()/../name]/service-obj-name";
        description
          "Enter ACL Rule Service Object Group Name";
        when "../protocol =  'object-group'";
      }
      leaf source-condition {
        type enumeration {
          enum "cidr";
          enum "host";
          enum "any";
          enum "objectgroup";
        }
        description
          "Enter ACL Rule Source Condition\n";
        n-ext:maps-to "/ac:devices/ac:device/acl:access-lists/access-list[name=current()/../../name]/acl-rules/acl-rule[name=current()/../name]/source-condition-type";
      }
      leaf source-object {
        type string-no-space;
        description
          "Enter ACL Rule Source Object Details (IPv4 Address/Prefix)";
        when "../source-condition =  'cidr' or ../source-condition =  'host'";
        n-ext:maps-to "/ac:devices/ac:device/acl:access-lists/access-list[name=current()/../../name]/acl-rules/acl-rule[name=current()/../name]/source-ip";
        n-ext:maps-to "/ac:devices/ac:device/acl:access-lists/access-list[name=current()/../../name]/acl-rules/acl-rule[name=current()/../name]";
        n-ext:prefix-maps-to "source-ip,source-mask";
      }
      leaf source-object-group {
        type leafref {
          path "/ac:services/cpedeployment:managed-cpe-services/customer[name=current()/../../../../name]/object-groups/object-group/name";
        }
        n-ext:maps-to "/ac:devices/ac:device/acl:access-lists/access-list[name=current()/../../name]/acl-rules/acl-rule[name=current()/../name]/source-obj-name";
        description
          "Enter ACL Rule Source Object Group";
        when "../source-condition =  'objectgroup'";
      }
      leaf source-port-operator {
        type enumeration {
          enum "eq";
          enum "range";
          enum "lt";
          enum "gt";
        }
        description
          "Enter ACL Rule TCP/UDP Source Port Operator\n";
        when "../protocol =  'tcp' or ../protocol =  'udp'";
        n-ext:maps-to "/ac:devices/ac:device/acl:access-lists/access-list[name=current()/../../name]/acl-rules/acl-rule[name=current()/../name]/source-port-operator";
      }
      leaf source-port {
        type string-no-lead-trail-space;
        description
          "0..65535";
        n-ext:maps-to "/ac:devices/ac:device/acl:access-lists/access-list[name=current()/../../name]/acl-rules/acl-rule[name=current()/../name]/source-port";
        //n-ext:maps-to "/ac:devices/device/acl:access-lists/access-list/acl-rules/acl-rule/source-port";
        when "../protocol =  'tcp' or ../protocol =  'udp'";
      }
      leaf destination-condition {
        type enumeration {
          enum "cidr";
          enum "host";
          enum "any";
          enum "objectgroup";
        }
        n-ext:maps-to "/ac:devices/ac:device/acl:access-lists/access-list[name=current()/../../name]/acl-rules/acl-rule[name=current()/../name]/dest-condition-type";
        //n-ext:maps-to "/ac:devices/device/acl:access-lists/access-list/acl-rules/acl-rule/dest-condition-type";
        description
          "Enter ACL Rule Destination Condition\n";
      }
      leaf destination-object {
        type string-no-space;
        description
          "Enter ACL Rule Destination Object Details (IPv4 Address/Prefix)";
        when "../destination-condition =  'cidr' or ../destination-condition =  'host'";
        n-ext:maps-to "/ac:devices/ac:device/acl:access-lists/access-list[name=current()/../../name]/acl-rules/acl-rule[name=current()/../name]/dest-ip";
        n-ext:maps-to "/ac:devices/ac:device/acl:access-lists/access-list[name=current()/../../name]/acl-rules/acl-rule[name=current()/../name]";
        n-ext:prefix-maps-to "dest-ip,dest-mask";
      }
      leaf destination-object-group {
        type leafref {
          path "/ac:services/cpedeployment:managed-cpe-services/customer[name=current()/../../../../name]/object-groups/object-group/name";
        }
        n-ext:maps-to "/ac:devices/ac:device/acl:access-lists/access-list[name=current()/../../name]/acl-rules/acl-rule[name=current()/../name]/dest-obj-name";
        description
          "Enter ACL Rule Destination Object Group";
        when "../destination-condition =  'objectgroup'";
      }
      leaf dest-port-operator {
        type enumeration {
          enum "eq";
          enum "range";
          enum "lt";
          enum "gt";
        }
        description
          "Enter ACL Rule TCP/UDP Destination Port Operator\n";
        when "../protocol =  'tcp' or ../protocol =  'udp'";
        n-ext:maps-to "/ac:devices/ac:device/acl:access-lists/access-list[name=current()/../../name]/acl-rules/acl-rule[name=current()/../name]/dest-port-operator";
      }
      leaf port-number {
        type string-no-lead-trail-space;
        description
          "Enter ACL Rule TCP/UDP Destination Port Operator";
        when "../protocol =  'tcp' or ../protocol =  'udp'";
        n-ext:maps-to "/ac:devices/ac:device/acl:access-lists/access-list[name=current()/../../name]/acl-rules/acl-rule[name=current()/../name]/dest-port";
      }
      leaf match-packets {
        type match-packets-type;
        description
          "Enter ACL Rule Match IP Packets ToS header (DSCP/Precence)";
        n-ext:maps-to "/ac:devices/ac:device/acl:access-lists/access-list[name=current()/../../name]/acl-rules/acl-rule[name=current()/../name]/match-packets";
      }
      leaf precedence {
        type precedence-type;
        description
          "Select IP Precence Type\n";
        when " ../match-packets = 'precedence' ";
        n-ext:maps-to "/ac:devices/ac:device/acl:access-lists/access-list[name=current()/../../name]/acl-rules/acl-rule[name=current()/../name]/precedence";
      }
      leaf dscp {
        type dscp-values-type;
        description
          "Select DSCP Value\n";
        when " ../match-packets = 'dscp' ";
        n-ext:maps-to "/ac:devices/ac:device/acl:access-lists/access-list[name=current()/../../name]/acl-rules/acl-rule[name=current()/../name]/precedence";
      }
      leaf sequence-number {
        type string;
        default "14";
        description
          "sequence-number";
        config false;
      }
    }
  }

  grouping update-acl-def {
    leaf id {
      type string-no-space;
      description
        "Enter Transaction ID. This is an internal field for Anuta NCX";
    }
    leaf update-acl-in-profile {
      type boolean;
      description
        "Check to update customer template";
    }
    leaf access-list-name {
      type leafref {
        path "/ac:services/cpedeployment:managed-cpe-services/customer[name=current()/../../../name]/access-lists/access-list/name";
      }
      description
        "access-list-name";
      mandatory true;
      //n-ext:maps-to "/ac:devices/device/acl:access-lists/access-list/name";
    }
    leaf rule-name {
      type string-no-lead-trail-space;
      description
        "Enter ACL Rule Name (eg: permit ip any any)";
      mandatory true;
    }
    leaf operation {
      type operation-def;
      description
        "CREATE
         DELETE
        ";
    }
    //leaf acl-name {
    //type string;
    //description
    //"string";
    //type leafref {
    //  path "/ac:services/cpedeployment:managed-cpe-services/customer[name=current()/../../../name]/access-lists/access-list[name=current()/../access-list-name]/access-list-rules/name";
    //}
    //mandatory true;
    //n-ext:maps-to "/ac:devices/device/acl:access-lists/access-list[name=current()/../../name]/acl-rules/acl-rule/name";
    //}
    leaf acl-sequence-num {
      type uint32 {
        range "1..2147483647";
      }
      description
        "1..2147483647";
      //n-ext:maps-to "/ac:devices/device/acl:access-lists/access-list[name=current()/../../name]/acl-rules/acl-rule[name=current()/../name]/linenumber";
    }
    leaf action {
      type enumeration {
        enum "permit";
        enum "deny";
      }
      description
        "permit
         deny
        ";
      mandatory true;
      //n-ext:maps-to "/ac:devices/device/acl:access-lists/access-list[name=current()/../../name]/acl-rules/acl-rule[name=current()/../name]/action";
    }
    leaf protocol {
      type enumeration {
        enum "ahp";
        enum "eigrp";
        enum "esp";
        enum "gre";
        enum "icmp";
        enum "igmp";
        enum "ip";
        enum "ipinip";
        enum "object-group";
        enum "ospf";
        enum "pcp";
        enum "pim";
        enum "tcp";
        enum "udp";
      }
      description
        "ahp
         eigrp
         esp
         gre
         icmp
         igmp
         ip
         ipinip
         object-group
         ospf
         pcp
         pim
         tcp
         udp
        ";
      //mandatory true;
      //n-ext:maps-to "/ac:devices/device/acl:access-lists/access-list[name=current()/../../name]/acl-rules/acl-rule[name=current()/../name]/layer4protocol";
    }
    leaf service-obj-name {
      type leafref {
        path "/ac:services/cpedeployment:managed-cpe-services/customer[name=current()/../../../name]/object-groups/object-group/name";
      }
      description
        "string";
      when "../protocol =  'object-group'";
      //n-ext:maps-to "/ac:devices/device/acl:access-lists/access-list/acl-rules/acl-rule/service-obj-name";
    }
    leaf source-condition {
      type enumeration {
        enum "cidr";
        enum "host";
        enum "any";
        enum "objectgroup";
      }
      description
        "cidr
         host
         any
         objectgroup
        ";
      //n-ext:maps-to "/ac:devices/device/acl:access-lists/access-list[name=current()/../../name]/acl-rules/acl-rule[name=current()/../name]/source-condition-type";
    }
    leaf source-object {
      type string-no-space;
      description
        "string";
      when "../source-condition =  'cidr' or ../source-condition =  'host'";
      //n-ext:maps-to "/ac:devices/device/acl:access-lists/access-list[name=current()/../../name]/acl-rules/acl-rule[name=current()/../name]/source-ip";
      //n-ext:maps-to "/ac:devices/device/acl:access-lists/access-list[name=current()/../../name]/acl-rules/acl-rule[name=current()/../name]";
      //n-ext:prefix-maps-to "source-ip,source-mask";
    }
    leaf source-object-group {
      type leafref {
        path "/ac:services/cpedeployment:managed-cpe-services/customer[name=current()/../../../name]/object-groups/object-group/name";
      }
      description
        "source-object-group";
      when "../source-condition =  'objectgroup'";
      //n-ext:maps-to "/ac:devices/device/acl:object-groups-acl/object-group/name";
      //n-ext:maps-to "/ac:devices/device/acl:access-lists/access-list[name=current()/../../name]/acl-rules/acl-rule[name=current()/../name]/source-obj-name";
    }
    leaf source-port-operator {
      type enumeration {
        enum "eq";
        enum "range";
        enum "lt";
        enum "gt";
      }
      description
        "eq
         range
        ";
      when "../protocol =  'tcp' or ../protocol =  'udp'";
    }
    leaf source-port {
      type string-no-lead-trail-space;
      description
        "0..65535";
      when "../protocol =  'tcp' or ../protocol =  'udp'";
    }
    leaf destination-condition {
      type enumeration {
        enum "cidr";
        enum "host";
        enum "any";
        enum "objectgroup";
      }
      description
        "cidr
         host
         any
         objectgroup
        ";
      //n-ext:maps-to "/ac:devices/device/acl:access-lists/access-list[name=current()/../../name]/acl-rules/acl-rule[name=current()/../name]/dest-condition-type";
    }
    leaf destination-object {
      type string-no-space;
      description
        "string";
      when "../destination-condition =  'cidr' or ../destination-condition =  'host'";
      //n-ext:maps-to "/ac:devices/device/acl:access-lists/access-list[name=current()/../../name]/acl-rules/acl-rule[name=current()/../name]/dest-ip";
      //n-ext:maps-to "/ac:devices/device[id=current()/../../../../device-ip]/acl:access-lists/access-list[name=current()/../../name]/acl-rules/acl-rule[name=current()/../name]";
      //n-ext:prefix-maps-to "dest-ip,dest-mask";
    }
    leaf destination-object-group {
      type leafref {
        path "/ac:services/cpedeployment:managed-cpe-services/customer[name=current()/../../../name]/object-groups/object-group/name";
      }
      description
        "destination-object-group";
      when "../destination-condition =  'objectgroup'";
      //n-ext:maps-to "/ac:devices/device/acl:object-groups-acl/object-group/name";
      //n-ext:maps-to "/ac:devices/device/acl:access-lists/access-list[name=current()/../../name]/acl-rules/acl-rule[name=current()/../name]/dest-obj-name";
    }
    leaf dest-port-operator {
      type enumeration {
        enum "eq";
        enum "range";
        enum "lt";
        enum "gt";
      }
      description
        "eq
         range
        ";
      when "../protocol =  'tcp' or ../protocol =  'udp'";
    }
    leaf port-number {
      type string-no-lead-trail-space;
      description
        "Enter Desintation Port Number";
      when "../protocol =  'tcp' or ../protocol =  'udp'";
    }
    leaf match-packets {
      type match-packets-type;
      description
        "precedence\n";
      //n-ext:maps-to "/ac:devices/device/acl:access-lists/access-list[name=current()/../../name]/acl-rules/acl-rule[name=current()/../name]/match-packets";
    }
    leaf precedence {
      type precedence-type;
      description
        "routine
         priority
         immediate
         flash
         flash-override
         critical
         internet
         network
        ";
      when " ../match-packets = 'precedence' ";
      //n-ext:maps-to "/ac:devices/device/acl:access-lists/access-list[name=current()/../../name]/acl-rules/acl-rule[name=current()/../name]/precedence";
    }
    leaf dscp {
      type dscp-values-type;
      description
        "Union Input types:
         enumeration
        ";
      when " ../match-packets = 'dscp' ";
      //n-ext:maps-to "/ac:devices/device/acl:access-lists/access-list[name=current()/../../name]/acl-rules/acl-rule[name=current()/../name]/precedence";
    }
    leaf apply-to-sites {
      type boolean;
      description
        "Check if you want to perform bulk update operation on individual sites";
      when "../apply-to-device-group = 'false'";
    }
    leaf apply-to-device-group {
      type boolean;
      description
        "Check if you want to perform bulk update operation on device group";
      when "../apply-to-sites = 'false'";
    }
    leaf device-group {
      type leafref {
        path "/ac:data-grouping/ac:definition/ac:name";
      }
      description
        "device-group";
      when "../apply-to-device-group = 'true'";
    }
    leaf single-cpe-site {
      type boolean;
      description
        "single-cpe-site: True/False";
      when "../apply-to-sites = 'true'";
    }
    leaf-list single-cpe-sites {
      type leafref {
        //path "../../../single-cpe-site/single-cpe-site-services/site-name";
        path "/ac:services/cpedeployment:managed-cpe-services/customer[name=current()/../../../name]/single-cpe-site/single-cpe-site-services/site-name";
        require-instance false;
      }
      description
        "single-sites";
      when " ../single-cpe-site = 'true' ";
    }
    leaf dual-cpe-site {
      type boolean;
      description
        "dual-cpe-site: True/False";
      when "../apply-to-sites = 'true'";
    }
    leaf-list dual-cpe-sites {
      type leafref {
        //path "../../../dual-cpe-site/dual-cpe-site-services/site-name";
        path "/ac:services/cpedeployment:managed-cpe-services/customer[name=current()/../../../name]/dual-cpe-site/dual-cpe-site-services/site-name";
        require-instance false;
      }
      description
        "dual-sites";
      when " ../dual-cpe-site = 'true' ";
    }
    leaf single-cpe-dual-wan-site {
      type boolean;
      description
        "single-cpe-dual-wan-site: True/False";
      when "../apply-to-sites = 'true'";
    }
    leaf-list single-cpe-dual-wan-sites {
      type leafref {
        //path "../../../single-cpe-dual-wan-site/single-cpe-dual-wan-site-services/site-name";
        path "/ac:services/cpedeployment:managed-cpe-services/customer[name=current()/../../../name]/single-cpe-dual-wan-site/single-cpe-dual-wan-site-services/site-name";
        require-instance false;
      }
      description
        "single-sites";
      when " ../single-cpe-dual-wan-site = 'true' ";
    }
    leaf dual-cpe-dual-wan-site {
      type boolean;
      description
        "dual-cpe-dual-wan-site: True/False";
      when "../apply-to-sites = 'true'";
    }
    leaf-list dual-cpe-dual-wan-sites {
      type leafref {
        //path "../../../dual-cpe-dual-wan-site/dual-cpe-dual-wan-site-services/site-name";
        path "/ac:services/cpedeployment:managed-cpe-services/customer[name=current()/../../../name]/dual-cpe-dual-wan-site/dual-cpe-dual-wan-site-services/site-name";
        require-instance false;
      }
      description
        "dual-sites";
      when " ../dual-cpe-dual-wan-site = 'true' ";
    }
    leaf triple-cpe-site {
      type boolean;
      description
        "triple-cpe-site: True/False";
      when "../apply-to-sites = 'true'";
    }
    leaf-list triple-cpe-sites {
      type leafref {
        //path "../../../triple-cpe-site/triple-cpe-site-services/site-name";
        path "/ac:services/cpedeployment:managed-cpe-services/customer[name=current()/../../../name]/triple-cpe-site/triple-cpe-site-services/site-name";
        require-instance false;
      }
      description
        "single-sites";
      when " ../triple-cpe-site = 'true' ";
    }
    list additional-acl-entry {
      key "id";
      leaf id {
        type string-no-space;
        description
          "Enter Unique ID. This is an internal field for Anuta NCX";
      }
      leaf rule-name {
        type string-no-lead-trail-space;
        description
          "Enter ACL Rule Name (eg: permit ip any any)";
        mandatory true;
      }
      leaf acl-sequence-num {
        type uint32 {
          range "1..2147483647";
        }
        description
          "1..2147483647";
        //n-ext:maps-to "/ac:devices/device/acl:access-lists/access-list[name=current()/../../name]/acl-rules/acl-rule[name=current()/../name]/linenumber";
      }
      leaf action {
        type enumeration {
          enum "permit";
          enum "deny";
        }
        description
          "permit
           deny
          ";
        mandatory true;
        //n-ext:maps-to "/ac:devices/device/acl:access-lists/access-list[name=current()/../../name]/acl-rules/acl-rule[name=current()/../name]/action";
      }
      leaf protocol {
        type enumeration {
          enum "ahp";
          enum "eigrp";
          enum "esp";
          enum "gre";
          enum "icmp";
          enum "igmp";
          enum "ip";
          enum "ipinip";
          enum "object-group";
          enum "ospf";
          enum "pcp";
          enum "pim";
          enum "tcp";
          enum "udp";
        }
        description
          "ahp
           eigrp
           esp
           gre
           icmp
           igmp
           ip
           ipinip
           object-group
           ospf
           pcp
           pim
           tcp
           udp
          ";
        //mandatory true;
        //n-ext:maps-to "/ac:devices/device/acl:access-lists/access-list[name=current()/../../name]/acl-rules/acl-rule[name=current()/../name]/layer4protocol";
      }
      leaf service-obj-name {
        type leafref {
          path "/ac:services/cpedeployment:managed-cpe-services/customer[name=current()/../../../../name]/object-groups/object-group/name";
        }
        description
          "string";
        when "../protocol =  'object-group'";
        //n-ext:maps-to "/ac:devices/device/acl:access-lists/access-list/acl-rules/acl-rule/service-obj-name";
      }
      leaf source-condition {
        type enumeration {
          enum "cidr";
          enum "host";
          enum "any";
          enum "objectgroup";
        }
        description
          "cidr
           host
           any
           objectgroup
          ";
        //n-ext:maps-to "/ac:devices/device/acl:access-lists/access-list[name=current()/../../name]/acl-rules/acl-rule[name=current()/../name]/source-condition-type";
      }
      leaf source-object {
        type string-no-space;
        description
          "string";
        when "../source-condition =  'cidr' or ../source-condition =  'host'";
        //n-ext:maps-to "/ac:devices/device/acl:access-lists/access-list[name=current()/../../name]/acl-rules/acl-rule[name=current()/../name]/source-ip";
        //n-ext:maps-to "/ac:devices/device/acl:access-lists/access-list[name=current()/../../name]/acl-rules/acl-rule[name=current()/../name]";
        //n-ext:prefix-maps-to "source-ip,source-mask";
      }
      leaf source-object-group {
        type leafref {
          path "/ac:services/cpedeployment:managed-cpe-services/customer[name=current()/../../../../name]/object-groups/object-group/name";
        }
        description
          "source-object-group";
        when "../source-condition =  'objectgroup'";
        //n-ext:maps-to "/ac:devices/device/acl:object-groups-acl/object-group/name";
        //n-ext:maps-to "/ac:devices/device/acl:access-lists/access-list[name=current()/../../name]/acl-rules/acl-rule[name=current()/../name]/source-obj-name";
      }
      leaf source-port-operator {
        type enumeration {
          enum "eq";
          enum "range";
          enum "lt";
          enum "gt";
        }
        description
          "eq
           range
          ";
        when "../protocol =  'tcp' or ../protocol =  'udp'";
      }
      leaf source-port {
        type string-no-lead-trail-space;
        description
          "0..65535";
        when "../protocol =  'tcp' or ../protocol =  'udp'";
      }
      leaf destination-condition {
        type enumeration {
          enum "cidr";
          enum "host";
          enum "any";
          enum "objectgroup";
        }
        description
          "cidr
           host
           any
           objectgroup
          ";
        //n-ext:maps-to "/ac:devices/device/acl:access-lists/access-list[name=current()/../../name]/acl-rules/acl-rule[name=current()/../name]/dest-condition-type";
      }
      leaf destination-object {
        type string-no-space;
        description
          "string";
        when "../destination-condition =  'cidr' or ../destination-condition =  'host'";
        //n-ext:maps-to "/ac:devices/device/acl:access-lists/access-list[name=current()/../../name]/acl-rules/acl-rule[name=current()/../name]/dest-ip";
        //n-ext:maps-to "/ac:devices/device[id=current()/../../../../device-ip]/acl:access-lists/access-list[name=current()/../../name]/acl-rules/acl-rule[name=current()/../name]";
        //n-ext:prefix-maps-to "dest-ip,dest-mask";
      }
      leaf destination-object-group {
        type leafref {
          path "/ac:services/cpedeployment:managed-cpe-services/customer[name=current()/../../../../name]/object-groups/object-group/name";
        }
        description
          "destination-object-group";
        when "../destination-condition =  'objectgroup'";
        //n-ext:maps-to "/ac:devices/device/acl:object-groups-acl/object-group/name";
        //n-ext:maps-to "/ac:devices/device/acl:access-lists/access-list[name=current()/../../name]/acl-rules/acl-rule[name=current()/../name]/dest-obj-name";
      }
      leaf dest-port-operator {
        type enumeration {
          enum "eq";
          enum "range";
          enum "lt";
          enum "gt";
        }
        description
          "eq
           range
          ";
        when "../protocol =  'tcp' or ../protocol =  'udp'";
      }
      leaf port-number {
        type string-no-lead-trail-space;
        description
          "Enter Destination Port Number";
        when "../protocol =  'tcp' or ../protocol =  'udp'";
      }
      leaf match-packets {
        type match-packets-type;
        description
          "precedence\n";
        //n-ext:maps-to "/ac:devices/device/acl:access-lists/access-list[name=current()/../../name]/acl-rules/acl-rule[name=current()/../name]/match-packets";
      }
      leaf precedence {
        type precedence-type;
        description
          "routine
           priority
           immediate
           flash
           flash-override
           critical
           internet
           network
          ";
        when " ../match-packets = 'precedence' ";
        //n-ext:maps-to "/ac:devices/device/acl:access-lists/access-list[name=current()/../../name]/acl-rules/acl-rule[name=current()/../name]/precedence";
      }
      leaf dscp {
        type dscp-values-type;
        description
          "Union Input types:
           enumeration
          ";
        when " ../match-packets = 'dscp' ";
        //n-ext:maps-to "/ac:devices/device/acl:access-lists/access-list[name=current()/../../name]/acl-rules/acl-rule[name=current()/../name]/precedence";
      }
    }
  }

  grouping delete-acl-def {
    leaf id {
      type string-no-space;
      description
        "Enter Transaction id
         This is an internal field for Anuta NCX";
    }
    leaf access-list-name {
      type leafref {
        path "/ac:services/cpedeployment:managed-cpe-services/customer[name=current()/../../../name]/access-lists/access-list/name";
      }
      description
        "Select ACL Name to Delete";
      mandatory true;
      //n-ext:maps-to "/ac:devices/device/acl:access-lists/access-list/name";
    }
    leaf single-cpe-site {
      type boolean;
      description
        "single-cpe-site: True/False";
    }
    leaf-list single-cpe-sites {
      type leafref {
        //path "../../../single-cpe-site/single-cpe-site-services/site-name";
        path "/ac:services/cpedeployment:managed-cpe-services/customer[name=current()/../../../name]/single-cpe-site/single-cpe-site-services/site-name";
        require-instance false;
      }
      description
        "single-sites";
      when " ../single-cpe-site = 'true' ";
    }
    leaf dual-cpe-site {
      type boolean;
      description
        "dual-cpe-site: True/False";
    }
    leaf-list dual-cpe-sites {
      type leafref {
        //path "../../../dual-cpe-site/dual-cpe-site-services/site-name";
        path "/ac:services/cpedeployment:managed-cpe-services/customer[name=current()/../../../name]/dual-cpe-site/dual-cpe-site-services/site-name";
        require-instance false;
      }
      description
        "dual-sites";
      when " ../dual-cpe-site = 'true' ";
    }
    leaf single-cpe-dual-wan-site {
      type boolean;
      description
        "single-cpe-dual-wan-site: True/False";
    }
    leaf-list single-cpe-dual-wan-sites {
      type leafref {
        //path "../../../single-cpe-dual-wan-site/single-cpe-dual-wan-site-services/site-name";
        path "/ac:services/cpedeployment:managed-cpe-services/customer[name=current()/../../../name]/single-cpe-dual-wan-site/single-cpe-dual-wan-site-services/site-name";
        require-instance false;
      }
      description
        "single-sites";
      when " ../single-cpe-dual-wan-site = 'true' ";
    }
    leaf dual-cpe-dual-wan-site {
      type boolean;
      description
        "dual-cpe-dual-wan-site: True/False";
    }
    leaf-list dual-cpe-dual-wan-sites {
      type leafref {
        //path "../../../dual-cpe-dual-wan-site/dual-cpe-dual-wan-site-services/site-name";
        path "/ac:services/cpedeployment:managed-cpe-services/customer[name=current()/../../../name]/dual-cpe-dual-wan-site/dual-cpe-dual-wan-site-services/site-name";
        require-instance false;
      }
      description
        "dual-sites";
      when " ../dual-cpe-dual-wan-site = 'true' ";
    }
    leaf triple-cpe-site {
      type boolean;
      description
        "triple-cpe-site: True/False";
    }
    leaf-list triple-cpe-sites {
      type leafref {
        //path "../../../triple-cpe-site/triple-cpe-site-services/site-name";
        path "/ac:services/cpedeployment:managed-cpe-services/customer[name=current()/../../../name]/triple-cpe-site/triple-cpe-site-services/site-name";
        require-instance false;
      }
      description
        "single-sites";
      when " ../triple-cpe-site = 'true' ";
    }
  }

  grouping delete-object-group-def {
    leaf id {
      type string-no-space;
      description
        "Enter Transaction id
         This is an internal field for Anuta NCX";
    }
    leaf object-group-name {
      type leafref {
        path "/ac:services/cpedeployment:managed-cpe-services/customer[name=current()/../../../name]/object-groups/object-group/name";
      }
      description
        "Select Object Group Name to Delete";
      mandatory true;
      //n-ext:maps-to "/ac:devices/device/acl:access-lists/access-list/name";
    }
    leaf single-cpe-site {
      type boolean;
      description
        "single-cpe-site: True/False";
    }
    leaf-list single-cpe-sites {
      type leafref {
        //path "../../../single-cpe-site/single-cpe-site-services/site-name";
        path "/ac:services/cpedeployment:managed-cpe-services/customer[name=current()/../../../name]/single-cpe-site/single-cpe-site-services/site-name";
        require-instance false;
      }
      description
        "single-sites";
      when " ../single-cpe-site = 'true' ";
    }
    leaf dual-cpe-site {
      type boolean;
      description
        "dual-cpe-site: True/False";
    }
    leaf-list dual-cpe-sites {
      type leafref {
        //path "../../../dual-cpe-site/dual-cpe-site-services/site-name";
        path "/ac:services/cpedeployment:managed-cpe-services/customer[name=current()/../../../name]/dual-cpe-site/dual-cpe-site-services/site-name";
        require-instance false;
      }
      description
        "dual-sites";
      when " ../dual-cpe-site = 'true' ";
    }
    leaf single-cpe-dual-wan-site {
      type boolean;
      description
        "single-cpe-dual-wan-site: True/False";
    }
    leaf-list single-cpe-dual-wan-sites {
      type leafref {
        //path "../../../single-cpe-dual-wan-site/single-cpe-dual-wan-site-services/site-name";
        path "/ac:services/cpedeployment:managed-cpe-services/customer[name=current()/../../../name]/single-cpe-dual-wan-site/single-cpe-dual-wan-site-services/site-name";
        require-instance false;
      }
      description
        "single-sites";
      when " ../single-cpe-dual-wan-site = 'true' ";
    }
    leaf dual-cpe-dual-wan-site {
      type boolean;
      description
        "dual-cpe-dual-wan-site: True/False";
    }
    leaf-list dual-cpe-dual-wan-sites {
      type leafref {
        //path "../../../dual-cpe-dual-wan-site/dual-cpe-dual-wan-site-services/site-name";
        path "/ac:services/cpedeployment:managed-cpe-services/customer[name=current()/../../../name]/dual-cpe-dual-wan-site/dual-cpe-dual-wan-site-services/site-name";
        require-instance false;
      }
      description
        "dual-sites";
      when " ../dual-cpe-dual-wan-site = 'true' ";
    }
    leaf triple-cpe-site {
      type boolean;
      description
        "triple-cpe-site: True/False";
    }
    leaf-list triple-cpe-sites {
      type leafref {
        //path "../../../triple-cpe-site/triple-cpe-site-services/site-name";
        path "/ac:services/cpedeployment:managed-cpe-services/customer[name=current()/../../../name]/triple-cpe-site/triple-cpe-site-services/site-name";
        require-instance false;
      }
      description
        "single-sites";
      when " ../triple-cpe-site = 'true' ";
    }
  }

  grouping feature-acl-def {
    leaf name {
      type string-no-space;
      description
        "string";
      n-ext:maps-to "/ac:devices/ac:device[ac:id=current()/../../../device-ip]/acl:access-lists/access-list/name";
    }
    leaf access-list-entry {
      type access-list-entry-type;
      description
        "standard
         extended
        ";
      default "extended";
      n-ext:maps-to "/ac:devices/ac:device[ac:id=current()/../../../device-ip]/acl:access-lists/access-list[name=current()/../name]/acl-type";
    }
    leaf sequence-number {
      type string;
      default "24";
      description
        "sequence-number";
      config false;
    }
    list access-list-rules {
      key "name action";
      leaf sequence-number {
        type string;
        default "25";
        description
          "sequence-number";
        config false;
      }
      leaf name {
        type string-no-lead-trail-space;
        description
          "string";
        n-ext:maps-to "/ac:devices/ac:device[ac:id=current()/../../../../device-ip]/acl:access-lists/access-list[name=current()/../../name]/acl-rules/acl-rule/name";
      }
      leaf action {
        type enumeration {
          enum "permit";
          enum "deny";
        }
        n-ext:maps-to "/ac:devices/ac:device[ac:id=current()/../../../../device-ip]/acl:access-lists/access-list[name=current()/../../name]/acl-rules/acl-rule[name=current()/../name]/action";
        description
          "permit
           deny
          ";
      }
      leaf protocol {
        type enumeration {
          enum "ahp";
          enum "eigrp";
          enum "esp";
          enum "gre";
          enum "icmp";
          enum "igmp";
          enum "ip";
          enum "ipinip";
          enum "object-group";
          enum "ospf";
          enum "pcp";
          enum "pim";
          enum "tcp";
          enum "udp";
        }
        n-ext:maps-to "/ac:devices/ac:device[ac:id=current()/../../../../device-ip]/acl:access-lists/access-list[name=current()/../../name]/acl-rules/acl-rule[name=current()/../name]/layer4protocol";
        description
          "ahp
           eigrp
           esp
           gre
           icmp
           igmp
           ip
           ipinip
           object-group
           ospf
           pcp
           pim
           tcp
           udp
          ";
      }
      leaf acl-sequence-num {
        type uint32 {
          range "1..2147483647";
        }
        description
          "1..2147483647";
        n-ext:maps-to "/ac:devices/ac:device[ac:id=current()/../../../../device-ip]/acl:access-lists/access-list[name=current()/../../name]/acl-rules/acl-rule[name=current()/../name]/linenumber";
      }
      leaf service-obj-name {
        type leafref {
          path "/ac:services/cpedeployment:managed-cpe-services/customer[name=current()/../../../../../../../name]/object-groups/object-group/name";
        }
        n-ext:maps-to "/ac:devices/ac:device[ac:id=current()/../../../../device-ip]/acl:access-lists/access-list[name=current()/../../name]/acl-rules/acl-rule[name=current()/../name]/service-obj-name";
        description
          "string";
        when "../protocol =  'object-group'";
      }
      leaf source-condition {
        type enumeration {
          enum "cidr";
          enum "host";
          enum "any";
          enum "objectgroup";
        }
        n-ext:maps-to "/ac:devices/ac:device[ac:id=current()/../../../../device-ip]/acl:access-lists/access-list[name=current()/../../name]/acl-rules/acl-rule[name=current()/../name]/source-condition-type";
        description
          "cidr
           host
           any
           objectgroup
          ";
      }
      leaf source-object {
        type string-no-space;
        description
          "string";
        when "../source-condition =  'cidr' or ../source-condition =  'host'";
        n-ext:maps-to "/ac:devices/ac:device[ac:id=current()/../../../../device-ip]/acl:access-lists/access-list[name=current()/../../name]/acl-rules/acl-rule[name=current()/../name]/source-ip";
        n-ext:maps-to "/ac:devices/ac:device[ac:id=current()/../../../../device-ip]/acl:access-lists/access-list[name=current()/../../name]/acl-rules/acl-rule[name=current()/../name]";
        n-ext:prefix-maps-to "source-ip,source-mask";
      }
      leaf source-object-group {
        type leafref {
          path "/ac:services/cpedeployment:managed-cpe-services/customer[name=current()/../../../../../../../name]/object-groups/object-group/name";
        }
        n-ext:maps-to "/ac:devices/ac:device[ac:id=current()/../../../../device-ip]/acl:object-groups-acl/object-group/name";
        description
          "source-object-group";
        when "../source-condition =  'objectgroup'";
      }
      leaf source-port-operator {
        type enumeration {
          enum "eq";
          enum "range";
          enum "lt";
          enum "gt";
        }
        description
          "eq
           range
          ";
        when "../protocol =  'tcp' or ../protocol =  'udp'";
        n-ext:maps-to "/ac:devices/ac:device[ac:id=current()/../../../../device-ip]/acl:access-lists/access-list[name=current()/../../name]/acl-rules/acl-rule[name=current()/../name]/source-port-operator";
      }
      leaf source-port {
        type string-no-lead-trail-space;
        description
          "0..65535";
        when "../protocol =  'tcp' or ../protocol =  'udp'";
        n-ext:maps-to "/ac:devices/ac:device[ac:id=current()/../../../../device-ip]/acl:access-lists/access-list[name=current()/../../name]/acl-rules/acl-rule[name=current()/../name]/source-port";
      }
      leaf destination-condition {
        type enumeration {
          enum "cidr";
          enum "host";
          enum "any";
          enum "objectgroup";
        }
        n-ext:maps-to "/ac:devices/ac:device[ac:id=current()/../../../../device-ip]/acl:access-lists/access-list[name=current()/../../name]/acl-rules/acl-rule[name=current()/../name]/dest-condition-type";
        description
          "cidr
           host
           any
           objectgroup
          ";
      }
      leaf destination-object {
        type string-no-space;
        description
          "string";
        when "../destination-condition =  'cidr' or ../destination-condition =  'host'";
        n-ext:maps-to "/ac:devices/ac:device[ac:id=current()/../../../../device-ip]/acl:access-lists/access-list[name=current()/../../name]/acl-rules/acl-rule[name=current()/../name]/dest-ip";
        n-ext:maps-to "/ac:devices/ac:device[ac:id=current()/../../../../device-ip]/acl:access-lists/access-list[name=current()/../../name]/acl-rules/acl-rule[name=current()/../name]";
        n-ext:prefix-maps-to "dest-ip,dest-mask";
      }
      leaf destination-object-group {
        type leafref {
          path "/ac:services/cpedeployment:managed-cpe-services/customer[name=current()/../../../../../../../name]/object-groups/object-group/name";
        }
        n-ext:maps-to "/ac:devices/ac:device[ac:id=current()/../../../../device-ip]/acl:object-groups-acl/object-group/name";
        description
          "destination-object-group";
        when "../destination-condition =  'objectgroup'";
      }
      leaf dest-port-operator {
        type enumeration {
          enum "eq";
          enum "range";
          enum "lt";
          enum "gt";
        }
        description
          "eq
           range
          ";
        when "../protocol =  'tcp' or ../protocol =  'udp'";
        n-ext:maps-to "/ac:devices/ac:device[ac:id=current()/../../../../device-ip]/acl:access-lists/access-list[name=current()/../../name]/acl-rules/acl-rule[name=current()/../name]/dest-port-operator";
      }
      leaf port-number {
        type string-no-lead-trail-space;
        description
          "Enter Destination Port Number";
        n-ext:maps-to "/ac:devices/ac:device[ac:id=current()/../../../../device-ip]/acl:access-lists/access-list[name=current()/../../name]/acl-rules/acl-rule[name=current()/../name]/dest-port";
        when "../protocol =  'tcp' or ../protocol =  'udp'";
      }
      leaf match-packets {
        type match-packets-type;
        description
          "precedence\n";
        n-ext:maps-to "/ac:devices/ac:device[ac:id=current()/../../../../device-ip]/acl:access-lists/access-list[name=current()/../../name]/acl-rules/acl-rule[name=current()/../name]/match-packets";
      }
      leaf precedence {
        type precedence-type;
        description
          "routine
           priority
           immediate
           flash
           flash-override
           critical
           internet
           network
          ";
        when " ../match-packets = 'precedence' ";
        n-ext:maps-to "/ac:devices/ac:device[ac:id=current()/../../../../device-ip]/acl:access-lists/access-list[name=current()/../../name]/acl-rules/acl-rule[name=current()/../name]/precedence";
      }
      leaf dscp {
        type dscp-values-type;
        description
          "Union Input types:
           enumeration
          ";
        when " ../match-packets = 'dscp' ";
        n-ext:maps-to "/ac:devices/ac:device[ac:id=current()/../../../../device-ip]/acl:access-lists/access-list[name=current()/../../name]/acl-rules/acl-rule[name=current()/../name]/precedence";
      }
    }
  }

  grouping dps-def {
    container dps {
      //n-ext:ignore-for-brownfield;
      list dps-services {
        n-ext:ncx-service;
        key "name";
        leaf name {
          type string-no-space;
          description
            "DPS Service Name";
        }
        leaf created-on {
          type string;
          description
            "string";
          config false;
        }
        leaf created-by {
          type string;
          description
            "string";
          config false;
        }
        leaf single-cpe-site {
          type boolean;
          description
            "Check if Single CPE Site Type";
          when " ../dual-cpe-site = 'false' and  ../single-cpe-dual-wan-site = 'false' and ../dual-cpe-dual-wan-site = 'false' and ../triple-cpe-site = 'false' ";
        }
        leaf single-cpe-sites {
          type leafref {
            path "../../../single-cpe-site/single-cpe-site-services/site-name";
          }
          description
            "Select Single CPE Site Name";
          when " ../single-cpe-site = 'true' ";
        }
        leaf dual-cpe-site {
          type boolean;
          description
            "Check if Dual CPE Site Type";
          when " ../single-cpe-site = 'false' and  ../single-cpe-dual-wan-site = 'false' and ../dual-cpe-dual-wan-site = 'false' and ../triple-cpe-site = 'false' ";
        }
        leaf dual-cpe-sites {
          type leafref {
            path "../../../dual-cpe-site/dual-cpe-site-services/site-name";
          }
          description
            "Select Dual CPE Site Name";
          when " ../dual-cpe-site = 'true' ";
        }
        leaf single-cpe-dual-wan-site {
          type boolean;
          description
            "Check if Single CPE Dual WAN Site Type";
          when " ../single-cpe-site = 'false' and  ../dual-cpe-site = 'false' and ../dual-cpe-dual-wan-site = 'false' and ../triple-cpe-site = 'false' ";
        }
        leaf single-cpe-dual-wan-sites {
          type leafref {
            path "../../../single-cpe-dual-wan-site/single-cpe-dual-wan-site-services/site-name";
          }
          description
            "Select Single CPE Dual WAN Site Name";
          when " ../single-cpe-dual-wan-site = 'true' ";
        }
        leaf dual-cpe-dual-wan-site {
          type boolean;
          description
            "Check if Dual CPE Dual WAN Site Type";
          when " ../single-cpe-site = 'false' and  ../dual-cpe-site = 'false' and  ../single-cpe-dual-wan-site = 'false' and ../triple-cpe-site = 'false' ";
        }
        leaf dual-cpe-dual-wan-sites {
          type leafref {
            path "../../../dual-cpe-dual-wan-site/dual-cpe-dual-wan-site-services/site-name";
          }
          description
            "Select Dual CPE Dual WAN Site Name";
          when " ../dual-cpe-dual-wan-site = 'true' ";
        }
        leaf triple-cpe-site {
          type boolean;
          description
            "Check if Triple CPE Site Type";
          when " ../single-cpe-site = 'false' and  ../dual-cpe-site = 'false' and  ../single-cpe-dual-wan-site = 'false' and ../dual-cpe-dual-wan-site = 'false' ";
        }
        leaf triple-cpe-sites {
          type leafref {
            path "../../../triple-cpe-site/triple-cpe-site-services/site-name";
          }
          description
            "Select Triple CPE Site Name";
          when " ../triple-cpe-site = 'true' ";
        }
        uses dps-domain-def;
      }
    }
  }

  grouping dps-domain-def {
    list cpe-name {
      key "cpe";
      leaf cpe {
        type enumeration {
          enum "cpe";
          enum "cpe-primary";
          enum "cpe-secondary";
          enum "cpe-secondary-only";
          //enum "cpe-primary-only";
          //enum "cpe-primary-dual";
          //enum "cpe-secondary-dual";
          //enum "cpe-primary-triple";
          //enum "cpe-secondary-only-dual";
        }
        description
          "- Select cpe to configure Single CPE / Single CPE Dual WAN
           - Select cpe-primary to configure Dual CPE / Triple CPE site Primary CPE
           - Select cpe-secondary to configure Dual CPE site Secondary CPE / Triple CPE Site Secondary CPE
           - Select cpe-secondary-only to configure Dual CPE Site with Secondary CPE as DPS controller
          ";
      }
      leaf vrf {
        type leafref {
          path "../../../../vrfs/vrf/vrf-name";
        }
        description
          "Select DPS VRF name";
        when " ../cpe = 'cpe' or ../cpe = 'cpe-secondary' or ../cpe = 'cpe-secondary-only' or ../cpe = 'cpe-primary-only'  or ../cpe = 'cpe-primary-triple'";
        n-ext:maps-to "/ac:devices/ac:device/l3:vrfs/vrf/name";
      }
      leaf rd {
        type string;
        description
          "string";
        when " ../cpe = 'cpe' or ../cpe = 'cpe-secondary' or ../cpe = 'cpe-secondary-only' or ../cpe = 'cpe-primary-only'  or ../cpe = 'cpe-primary-triple'";
        config false;
      }
      leaf rt-import {
        type string;
        description
          "string";
        when " ../cpe = 'cpe' or ../cpe = 'cpe-secondary' or ../cpe = 'cpe-secondary-only' or ../cpe = 'cpe-primary-only'  or ../cpe = 'cpe-primary-triple'";
        config false;
      }
      leaf rt-export {
        type string;
        description
          "string";
        when " ../cpe = 'cpe' or ../cpe = 'cpe-secondary' or ../cpe = 'cpe-secondary-only' or ../cpe = 'cpe-primary-only'  or ../cpe = 'cpe-primary-triple'";
        config false;
      }
      leaf lan-interface {
        type boolean;
        description
          "Check to configure DPS Controller LAN interface
           The LAN interface name is automatically selected from the CPE site service
          ";
        when " ../cpe = 'cpe' or ../cpe = 'cpe-primary' or ../cpe = 'cpe-secondary-only' or ../cpe = 'cpe-primary-only'  or ../cpe = 'cpe-primary-triple'";
      }
      leaf hierarchical-inbound-policy {
        type boolean;
        description
          "Check to apply HQOS policy on DPS controller LAN interface";
        when " ../lan-interface = 'true' and ../cpe != 'cpe-secondary'";
      }
      leaf hierarchical-policy {
        type leafref {
          path "../../../../qos-service/hierarchical-policy/policy/name";
        }
        description
          "Select HQOS policy to be applied on DPS controller LAN interface";
        when "../hierarchical-inbound-policy = 'true'";
      }
      leaf inbound-policy {
        type leafref {
          path "../../../../qos-service/policies/policy/name";
        }
        description
          "Select QoS policy to be applied on DPS controller LAN interface";
        when " ../lan-interface = 'true' and ../cpe != 'cpe-secondary' and ../hierarchical-inbound-policy = 'false'";
      }
      leaf pbr-policy {
        type leafref {
          path "../../../../route-maps/route-map/route-map-name";
        }
        description
          "Select PBR policy to be applied on DPS controller CPE";
        when " ../lan-interface = 'true' and ../cpe != 'cpe-secondary' ";
      }
      leaf next-hop-ip {
        type inet:ipv4-address;
        description
          "Enter PBR Next-Hop IP Address (set ip next-hop)
           If your PBR Route-map has the 'IP' keyword configured, the keyword will be replaced by this IP
          ";
        when " ../lan-interface = 'true' and ../cpe = 'cpe-primary'";
      }
      leaf vrf-receive {
        type boolean;
        description
          "Check to configure VRF Selection feature on LAN interface";
        when " ../lan-interface = 'true' and ../cpe != 'cpe-secondary' and ../cpe != 'cpe-primary'";
      }
      leaf bgp-policy {
        type boolean;
        description
          "Check to configure LAN QPPB policy IP Precedence based";
        when " ../lan-interface = 'true' and ../cpe != 'cpe-secondary'";
      }
      leaf bgp-policy-qos {
        type boolean;
        description
          "Check to configure LAN QPPB policy QoS Group based";
        when " ../lan-interface = 'true' and ../cpe != 'cpe-secondary'";
      }
      leaf b2b-interface {
        type boolean;
        description
          "Check to configure B2B interface for DPS
           The interface name will be automatically selected from the CPE site service
          ";
        when " ../cpe = 'cpe-secondary' or ../cpe = 'cpe-primary' ";
      }
      leaf vlan-id {
        type uint32 {
          range "1..4096";
        }
        description
          "Enter DPS B2B interface VLAN ID";
        when " ../b2b-interface = 'true' and ../cpe != 'cpe'";
      }
      leaf cidr {
        type leafref {
          path "/ip:ipaddress-pools/ip:ipaddress-pool/ip:name";
        }
        n-ext-ui:ncx-ext-pagination "paginate";
        description
          "Select DPS B2B Subnet";
        mandatory true;
        when " ../b2b-interface = 'true' and ../cpe != 'cpe'";
      }
      leaf interface-ip {
        type inet:ipv4-address;
        description
          "Enter DPS B2B interface IP Address";
        when " ../b2b-interface = 'true' and ../cpe != 'cpe'";
      }
      leaf b2b-description {
        type string;
        description
          "Enter DPS B2B interface description";
        when " ../b2b-interface = 'true' and ../cpe != 'cpe'";
      }
      leaf loopback {
        type boolean;
        description
          "Check to configure DPS Loopback";
        when " ../cpe = 'cpe' or ../cpe = 'cpe-secondary' or ../cpe = 'cpe-secondary-only' or ../cpe = 'cpe-primary-only'";
      }
      leaf loopback-interface-id {
        type uint8;
        description
          "Enter DPS Loopback Interface ID";
        when " ../loopback = 'true' and ../cpe != 'cpe-primary'";
      }
      leaf description {
        type string;
        description
          "Enter DPS Loopback Description";
        when " ../loopback = 'true' and ../cpe != 'cpe-primary'";
      }
      leaf cidr-loopback {
        type leafref {
          path "/ip:ipaddress-pools/ip:ipaddress-pool/ip:name";
        }
        n-ext-ui:ncx-ext-pagination "paginate";
        description
          "Select DPS Loopback Subnet";
        when " ../loopback = 'true' and ../cpe != 'cpe-primary'";
      }
      leaf loopback-ip {
        type inet:ipv4-address;
        description
          "Enter DPS Loopback IP Address";
        when " ../loopback = 'true' and ../cpe != 'cpe-primary'";
      }
      leaf ospf {
        type boolean;
        description
          "Check to configure DPS OSPF process";
      }
      leaf ospf-id {
        type uint16;
        description
          "Enter DPS OSPF Process ID";
        when " ../ospf = 'true' ";
      }
      leaf router-id {
        type inet:ip-address;
        description
          "Enter DPS OSPF Router-ID";
        when " ../ospf = 'true' and ../cpe != 'cpe-secondary'";
      }
      leaf static-route-map {
        type leafref {
          path "../../../../route-maps/route-map/route-map-name";
        }
        description
          "Select Static to OSPF Redistribution Route-Map";
        when " ../ospf = 'true' and ../cpe != 'cpe-secondary'";
      }
      leaf connected-route-map {
        type leafref {
          path "../../../../route-maps/route-map/route-map-name";
        }
        description
          "Select Connected to OSPF Redistribution Route-Map
           If the Route-Map has 'LAN-INTERFACE' keyword, it will be automatically replaced by the DPS Controller LAN interface name
          ";
        when " ../ospf = 'true' and ../cpe != 'cpe-secondary'";
      }
      leaf lan-ospf-redistribution {
        type boolean;
        description
          "Check to redistribute Customer LAN OSPF into DPS OSPF";
        when " ../ospf = 'true' and ../cpe != 'cpe-secondary'";
      }
      leaf ospf-route-map {
        type leafref {
          path "../../../../route-maps/route-map/route-map-name";
        }
        description
          "Select Customer LAN OSPF into DPS OSPF redistribution Route-Map";
        when " ../ospf = 'true' and ../lan-ospf-redistribution = 'true' and ../cpe != 'cpe-secondary'";
      }
      leaf ospf-key1 {
        type key;
        description
          "string";
        when " ../ospf = 'true' and ../lan-ospf-redistribution = 'true' and ../cpe != 'cpe-secondary'";
        config false;
      }
      leaf ospf-key2 {
        type key;
        description
          "string";
        when " ../ospf = 'true' and ../lan-ospf-redistribution = 'true' and ../cpe != 'cpe-secondary'";
        config false;
      }
      leaf ospf-metric {
        type uint32 {
          range "0..16777214";
        }
        description
          "Enter Customer LAN OSPF into DPS OSPF Redistribution Metric";
        when " ../ospf = 'true' and ../lan-ospf-redistribution = 'true' and ../cpe != 'cpe-secondary'";
      }
      leaf ospf-metric-type {
        type uint8 {
          range "1..2";
        }
        description
          "Enter Customer LAN OSPF into DPS OSPF Redistribution Metric Type";
        when " ../ospf = 'true' and ../lan-ospf-redistribution = 'true' and ../cpe != 'cpe-secondary'";
      }
      leaf ospf-tag {
        type uint32 {
          range "0..4294967295";
        }
        description
          "Enter Customer LAN OSPF into DPS OSPF Redistribution Tag";
        when " ../ospf = 'true' and ../lan-ospf-redistribution = 'true' and ../cpe != 'cpe-secondary'";
      }
      leaf ospf-redistribution-id {
        type uint16;
        description
          "Enter Customer LAN OSPF Process ID to be redistributed into DPS OSPF";
        when " ../ospf = 'true' and ../lan-ospf-redistribution = 'true' and ../cpe != 'cpe-secondary'";
      }
      leaf lan-ebgp-redistribution {
        type boolean;
        description
          "Check to Redistribute BGP into DPS OSPF";
        when " ../ospf = 'true' and ../cpe != 'cpe-secondary'";
      }
      leaf bgp-route-map {
        type leafref {
          path "../../../../route-maps/route-map/route-map-name";
        }
        description
          "Select BGP to DPS OSPF Redistribution Route-Map";
        when " ../ospf = 'true' and ../lan-ebgp-redistribution = 'true' and ../cpe != 'cpe-secondary'";
      }
      leaf bgp-key1 {
        type key;
        description
          "string";
        when " ../ospf = 'true' and ../lan-ebgp-redistribution = 'true' and ../cpe != 'cpe-secondary'";
        config false;
      }
      leaf bgp-key2 {
        type key;
        description
          "string";
        when " ../ospf = 'true' and ../lan-ebgp-redistribution = 'true' and ../cpe != 'cpe-secondary'";
        config false;
      }
      leaf bgp-metric {
        type uint32 {
          range "0..16777214";
        }
        description
          "Enter BGP to DPS OSPF Redistribution Metric";
        when " ../ospf = 'true' and ../lan-ebgp-redistribution = 'true' and ../cpe != 'cpe-secondary'";
      }
      leaf bgp-metric-type {
        type uint8 {
          range "1..2";
        }
        description
          "Enter BGP to DPS OSPF Redistribution Metric Type";
        when " ../ospf = 'true' and ../lan-ebgp-redistribution = 'true' and ../cpe != 'cpe-secondary'";
      }
      leaf bgp-tag {
        type uint32 {
          range "0..4294967295";
        }
        description
          "Enter BGP to DPS OSPF Redistribute Tag";
        when " ../ospf = 'true' and ../lan-ebgp-redistribution = 'true' and ../cpe != 'cpe-secondary'";
      }
      leaf lan-eigrp-redistribution {
        type boolean;
        when " ../ospf = 'true' and ../cpe != 'cpe-secondary'";
        description
          "Check to Redistribute LAN EIGRP process into DPS OSPD process";
      }
      leaf eigrp-as {
        type uint16 {
          range "1..65535";
        }
        description
          "1..65535";
        when " ../ospf = 'true' and ../lan-eigrp-redistribution = 'true' and ../cpe != 'cpe-secondary'";
      }
      leaf eigrp-route-map {
        type leafref {
          path "../../../../route-maps/route-map/route-map-name";
        }
        description
          "Select EIGRP to DPS OSPF Redistribution Route-Map";
        when " ../ospf = 'true' and ../lan-eigrp-redistribution = 'true' and ../cpe != 'cpe-secondary'";
      }
      leaf eigrp-metric {
        type uint32 {
          range "0..16777214";
        }
        description
          "Enter EIGRP to DPS OSPF Redistribution Metric";
        when " ../ospf = 'true' and ../lan-eigrp-redistribution = 'true' and ../cpe != 'cpe-secondary'";
      }
      leaf eigrp-metric-type {
        type uint8 {
          range "1..2";
        }
        description
          "Enter EIGRP to DPS OSPF Redistribution Metric Type";
        when " ../ospf = 'true' and ../lan-eigrp-redistribution = 'true' and ../cpe != 'cpe-secondary'";
      }
      leaf eigrp-tag {
        type uint32 {
          range "0..4294967295";
        }
        description
          "Enter EIGRP to DPS OSPF Redistribute Tag";
        when " ../ospf = 'true' and ../lan-eigrp-redistribution = 'true' and ../cpe != 'cpe-secondary'";
      }
      leaf vrf-lite {
        type boolean;
        description
          "Check to configure VRF-Lite Capability under the DPS OSPF process";
        when " ../ospf = 'true'";
      }
      container ospf-networks {
        list ospf-network {
          key "name";
          uses ospf-network-def;
        }
      }
      leaf bgp {
        type boolean;
        description
          "Check to configure BGP related configuration for DPS";
      }
      leaf bgp-vrf {
        type leafref {
          path "../../../../vrfs/vrf/vrf-name";
        }
        description
          "Select VRF name if CPE BGP peering(s) are configured under ipv4 vrf address family";
        when " ../bgp = 'true' and ../cpe != 'cpe-secondary'";
      }
      leaf qppb-policy {
        type leafref {
          path "../../../../route-maps/route-map/route-map-name";
        }
        description
          "Select BGP QPPB Policy";
        when " ../bgp = 'true' and ../cpe != 'cpe-secondary'";
      }
      leaf redistribute-connected {
        type leafref {
          path "../../../../route-maps/route-map/route-map-name";
        }
        description
          "Select Connected to BGP Redistribute Policy
           This setting is useful if you want to override previous policy applied during site creation
          ";
        when " ../bgp = 'true' and ../cpe != 'cpe-secondary'";
      }
      leaf redistribute-static {
        type leafref {
          path "../../../../route-maps/route-map/route-map-name";
        }
        description
          "Select Static to BGP Redistribute Policy
           This setting is useful if you want to override previous policy applied during site creation
          ";
        when " ../bgp = 'true' and ../cpe != 'cpe-secondary'";
      }
      leaf import-route-map {
        type leafref {
          path "../../../../route-maps/route-map/route-map-name";
        }
        description
          "Select WAN eBGP Inbound Route-Map
           This setting is useful if you want to override previous policy applied during site creation
          ";
        when " ../bgp = 'true' and ../cpe != 'cpe-secondary'";
      }
      leaf tunnel {
        type boolean;
        description
          "Check to configure DPS DMVPN overlay tunnel";
        when " ../cpe = 'cpe' or ../cpe = 'cpe-secondary' or ../cpe = 'cpe-secondary-only' or ../cpe = 'cpe-primary-only'";
      }
      leaf hub {
        type boolean;
        description
          "Check if the CPE configured is the DPS DMVPN hub";
        when " ../tunnel = 'true' and ../cpe != 'cpe-primary'";
      }
      leaf dmvpn-profile {
        type leafref {
          path "../../../../dmvpn-tunnel-profiles/dmvpn-tunnel-profile/name";
        }
        description
          "Select DPS DMVPN profile";
        when " ../tunnel = 'true' and ../cpe != 'cpe-primary'";
      }
      leaf tunnel-interface-ip-address {
        type inet:ipv4-address;
        description
          "Enter DPS DMVPN Tunnel interface IP address";
        when " ../tunnel = 'true' and ../cpe != 'cpe-primary'";
      }
      leaf tunnel-bandwidth {
        type uint32 {
          range "1..100000000";
        }
        description
          "Enter DPS DMVPN Tunnel interface bandwidth";
        when " ../tunnel = 'true' and ../cpe != 'cpe-primary'";
      }
      leaf tunnel-interface-description {
        type string-no-lead-trail-space;
        description
          "Enter DPS DMVPN Tunnel interface description";
        when " ../tunnel = 'true' and ../cpe != 'cpe-primary'";
      }
      leaf tunnel-fvrf {
        type leafref {
          path "../../../../vrfs/vrf/vrf-name";
        }
        description
          "Select DPS DMVPN Tunnel Front-End VRF
           This setting will configure 'tunnel vrf' under the DMVPN tunnnel interface
          ";
        when " ../tunnel = 'true' and ../cpe != 'cpe-primary'";
      }
      container advertise-networks {
        list advertise-network {
          key "name";
          uses advertise-network-dps;
        }
      }
      container static-routes {
        list static-route {
          key "dest-ip-address dest-mask";
          uses static-route;
        }
      }
      container route-maps {
        uses dps-route-maps-def-list;
      }
      container community-lists {
        uses community-lists-ref-def;
      }
      //container extcommunity-lists {
      //  uses extcommunity-lists-ref-def;
      //}
      container prefix-lists {
        uses dps-prefix-lists-def-list;
      }
    }
  }

  grouping adaptive-dps {
    list adaptive-dps-eem-applet-services {
      key "transaction-id";
      leaf transaction-id {
        type string-no-space;
        description
          "Enter Unique Transaction ID. This is an internal field for Anuta NCX";
      }
      leaf applet-name {
        type string;
        description
          "Name of the Event Manager applet";
        // n-ext:maps-to "/ac:devices/ac:device/l3:eem-applets/event-manager-applet/applet-name";
      }
      //      leaf device-ip {
      //        type leafref {
      //          path "/ac:devices/ac:device/ac:id";
      //        }
      //        description
      //          "device-ip";
      //        mandatory true; 
      //      } 
      leaf single-cpe-site {
        type boolean;
        description
          "single-cpe-site: True/False";
        when " ../dual-cpe-site = 'false' and  ../single-cpe-dual-wan-site = 'false' and ../dual-cpe-dual-wan-site = 'false' and ../triple-cpe-site = 'false' ";
      }
      leaf single-cpe-sites {
        type leafref {
          path "../../../single-cpe-site/single-cpe-site-services/site-name";
        }
        description
          "single-sites";
        when " ../single-cpe-site = 'true' ";
      }
      leaf dual-cpe-site {
        type boolean;
        description
          "dual-cpe-site: True/False";
        when " ../single-cpe-site = 'false' and  ../single-cpe-dual-wan-site = 'false' and ../dual-cpe-dual-wan-site = 'false' and ../triple-cpe-site = 'false' ";
      }
      leaf dual-cpe-sites {
        type leafref {
          path "../../../dual-cpe-site/dual-cpe-site-services/site-name";
        }
        description
          "dual-sites";
        when " ../dual-cpe-site = 'true' ";
      }
      leaf single-cpe-dual-wan-site {
        type boolean;
        description
          "single-cpe-dual-wan-site: True/False";
        when " ../single-cpe-site = 'false' and  ../dual-cpe-site = 'false' and ../dual-cpe-dual-wan-site = 'false' and ../triple-cpe-site = 'false' ";
      }
      leaf single-cpe-dual-wan-sites {
        type leafref {
          path "../../../single-cpe-dual-wan-site/single-cpe-dual-wan-site-services/site-name";
        }
        description
          "single-sites";
        when " ../single-cpe-dual-wan-site = 'true' ";
      }
      leaf dual-cpe-dual-wan-site {
        type boolean;
        description
          "dual-cpe-dual-wan-site: True/False";
        when " ../single-cpe-site = 'false' and  ../dual-cpe-site = 'false' and  ../single-cpe-dual-wan-site = 'false' and ../triple-cpe-site = 'false' ";
      }
      leaf dual-cpe-dual-wan-sites {
        type leafref {
          path "../../../dual-cpe-dual-wan-site/dual-cpe-dual-wan-site-services/site-name";
        }
        description
          "dual-dual-wan-sites";
        when " ../dual-cpe-dual-wan-site = 'true' ";
      }
      leaf triple-cpe-site {
        type boolean;
        description
          "triple-cpe-site: True/False";
        when " ../single-cpe-site = 'false' and  ../dual-cpe-site = 'false' and  ../single-cpe-dual-wan-site = 'false' and ../dual-cpe-dual-wan-site = 'false' ";
      }
      leaf triple-cpe-sites {
        type leafref {
          path "../../../triple-cpe-site/triple-cpe-site-services/site-name";
        }
        description
          "dual-dual-wan-sites";
        when " ../triple-cpe-site = 'true' ";
      }
      leaf cpe {
        type enumeration {
          enum "cpe";
          enum "cpe-primary";
          enum "cpe-secondary";
          enum "cpe-tertiary";
        }
        description
          "cpe
           cpe-primary
           cpe-secondary
           cpe-tertiary
          ";
      }
      container trigger {
        leaf delay-time {
          type uint32 {
            range "0..4294967295";
          }
          description
            "Time to delay raising event after all conditions met";
        }
        leaf occurrences-no {
          type uint32 {
            range "0..4294967295";
          }
          description
            "The number of occurrences before raising the event";
        }
        leaf period {
          type uint32 {
            range "0..4294967295";
          }
          description
            "Number of occurrences must occur within this time period";
        }
        leaf period-start {
          type string;
          description
            "Cron entry string";
        }
        container correlate {
          leaf event1 {
            type string;
            description
              "event tag value";
          }
          leaf logic {
            type enumeration {
              enum "and";
              enum "andnot";
              enum "or";
            }
            description
              "and
               andnot
               or
              ";
          }
          leaf event2 {
            type string;
            description
              "event tag value";
          }
        }
      }
      container events {
        list tag {
          key "tag-number";
          leaf tag-number {
            type uint32;
            description
              "0..4294967295";
            // n-ext:maps-to "/ac:devices/ac:device/l3:eem-applets/event-manager-applet/events/tag/tag-number";
          }
          leaf interface-name {
            type string;
            description
              "string";
            // n-ext:maps-to "/ac:devices/ac:device/l3:eem-applets/event-manager-applet/events/tag/interface-name";
          }
          leaf parameter {
            type enumeration {
              enum "rxload";
              enum "txload";
            }
            description
              "Interface counter to monitor";
            // n-ext:maps-to "/ac:devices/ac:device/l3:eem-applets/event-manager-applet/events/tag/parameter";
          }
          leaf entry-compare {
            type enumeration {
              enum "le";
              enum "ge";
            }
            description
              "Entry comparison operator";
            // n-ext:maps-to "/ac:devices/ac:device/l3:eem-applets/event-manager-applet/events/tag/entry-compare";
          }
          leaf entry-counter-val {
            type uint32;
            description
              "Counter value be compared to raise interface event";
            // n-ext:maps-to "/ac:devices/ac:device/l3:eem-applets/event-manager-applet/events/tag/entry-counter-val";
          }
          leaf poll-interval {
            type uint32;
            description
              "Interval between consecutive polls in seconds";
            // n-ext:maps-to "/ac:devices/ac:device/l3:eem-applets/event-manager-applet/events/tag/poll-interval";
          }
        }
      }
      container actions {
        list action {
          key "label";
          leaf label {
            type string;
            description
              "string";
            // n-ext:maps-to "/ac:devices/ac:device/l3:eem-applets/event-manager-applet/actions/action/label";
          }
          leaf action-statement {
            type enumeration {
              enum "cli";
              enum "regexp";
              enum "syslog";
              enum "if";
              enum "else";
              enum "exit";
              enum "comment";
              enum "end";
              enum "handle-error";
            }
            description
              "Add or modify an action statement";
            // n-ext:maps-to "/ac:devices/ac:device/l3:eem-applets/event-manager-applet/actions/action/action-statement";
          }
          leaf cli-type {
            type enumeration {
              enum "command";
              enum "pattern";
            }
            description
              "command
               pattern
              ";
            when "../action-statement = 'cli'";
            // n-ext:maps-to "/ac:devices/ac:device/l3:eem-applets/event-manager-applet/actions/action/cli-type";
          }
          leaf cli-string {
            type string;
            description
              "string";
            when "../action-statement = 'cli'";
            // n-ext:maps-to "/ac:devices/ac:device/l3:eem-applets/event-manager-applet/actions/action/cli-string";
          }
          leaf regex-pattern {
            type string;
            description
              "regular expression pattern";
            when "../action-statement = 'regexp'";
            // n-ext:maps-to "/ac:devices/ac:device/l3:eem-applets/event-manager-applet/actions/action/regex-pattern";
          }
          leaf input-string {
            type string;
            description
              "string";
            when "../action-statement = 'regexp'";
            // n-ext:maps-to "/ac:devices/ac:device/l3:eem-applets/event-manager-applet/actions/action/input-string";
          }
          leaf syslog-priority {
            type enumeration {
              enum "alerts";
              enum "critical";
              enum "debugging";
              enum "emergencies";
              enum "errors";
              enum "informational";
              enum "notifications";
              enum "warnings";
            }
            description
              "alerts
               critical
               debugging
               emergencies
               errors
               informational
               notifications
               warnings
              ";
            when "../action-statement = 'syslog'";
            // n-ext:maps-to "/ac:devices/ac:device/l3:eem-applets/event-manager-applet/actions/action/syslog-priority";
          }
          leaf syslog-type {
            type enumeration {
              enum "priority";
              enum "msg";
            }
            description
              "priority
               msg
              ";
            when "../action-statement = 'syslog'";
          }
          leaf syslog-msg {
            type string;
            description
              "string";
            when "../action-statement = 'syslog'";
            // n-ext:maps-to "/ac:devices/ac:device/l3:eem-applets/event-manager-applet/actions/action/syslog-msg";
          }
          leaf first-operand {
            type string;
            description
              "string";
            when "../action-statement = 'if'";
            // n-ext:maps-to "/ac:devices/ac:device/l3:eem-applets/event-manager-applet/actions/action/first-operand";
          }
          leaf compare {
            type enumeration {
              enum "eq";
              enum "ge";
              enum "lt";
            }
            description
              "eq
               ge
               lt
              ";
            when "../action-statement = 'if'";
            // n-ext:maps-to "/ac:devices/ac:device/l3:eem-applets/event-manager-applet/actions/action/compare";
          }
          leaf second-operand {
            type string;
            description
              "string";
            when "../action-statement = 'if'";
            // n-ext:maps-to "/ac:devices/ac:device/l3:eem-applets/event-manager-applet/actions/action/second-operand";
          }
          leaf exit-result {
            type string;
            description
              "string";
            when "../action-statement = 'exit'";
            // n-ext:maps-to "/ac:devices/ac:device/l3:eem-applets/event-manager-applet/actions/action/exit-result";
          }
          leaf comment-string {
            type string;
            description
              "string";
            when "../action-statement = 'comment'";
            // n-ext:maps-to "/ac:devices/ac:device/l3:eem-applets/event-manager-applet/actions/action/comment-string";
          }
          leaf handle-error-type {
            type enumeration {
              enum "exit";
              enum "ignore";
              enum "warn";
            }
            description
              "exit
               ignore
               warn
              ";
            when "../action-statement = 'handle-error'";
            // n-ext:maps-to "/ac:devices/ac:device/l3:eem-applets/event-manager-applet/actions/action/handle-error-type";
          }
        }
      }
    }
  }

  grouping static-route {
    leaf dest-ip-address {
      type inet:ipv4-address;
      description
        "Enter Static Route Destination Subnet";
      mandatory true;
    }
    leaf dest-mask {
      type inet:ipv4-address;
      description
        "Enter Static Route Destination Subnet Mask";
      mandatory true;
    }
    leaf next-hop-ip {
      type inet:ipv4-address;
      description
        "Enter Static Route Next-Hop IP";
      config false;
    }
    leaf description {
      type string;
      description
        "Enter Static Route Description";
      config false;
    }
    leaf metric {
      type uint32;
      description
        "0..4294967295";
      config false;
    }
    leaf interface-name {
      type string;
      description
        "interface-name";
      config false;
    }
    leaf seq-num {
      type uint32;
      description
        "0..4294967295";
      config false;
    }
    leaf name {
      type string;
      description
        "string";
      config false;
    }
    leaf vrf {
      description
        "name";
      type string;
      config false;
    }
    leaf tag {
      type uint32;
      description
        "0..4294967295";
      config false;
    }
    list options {
      key "id";
      leaf id {
        type string;
        description
          "Enter Static Route ID
           This is an internal field for Anuta NCX to differentiate static route options
          ";
      }
      leaf next-hop-ip {
        type inet:ipv4-address;
        description
          "Enter Static Route Next-Hop IP";
      }
      leaf global-address {
        type boolean;
        description
          "Check if Static Route should use next-hop in global Routing Table";
      }
      leaf metric {
        type uint32;
        description
          "Enter Static Route Metric";
      }
      leaf interface-name {
        type string;
        description
          "Enter Static Route Outbound Interface";
      }
      leaf name {
        type string-no-lead-trail-space;
        description
          "Enter Static Route Name";
      }
      leaf vrf {
        description
          "Select Static Route VRF";
        type leafref {
          path "../../../../../../../vrfs/vrf/vrf-name";
        }
      }
      leaf tag {
        type uint32;
        description
          "Enter Static Route tag value";
      }
      leaf track {
        type uint16;
        description
          "Enter Static Route track object value";
      }
      leaf permanent {
        type boolean;
        description
          "Check if permanent static route";
      }
    }
  }

  grouping crypto-isakmp-peer-def {
    leaf peer-address {
      type inet:ipv4-address;
      description
        "Enter Crypto ISAKMP Peer IPv4 Address";
      n-ext:maps-to "/ac:devices/ac:device[ac:id=current()/../../../device-ip]/dmvpn:crypto-peers/dmvpn:crypto-peer/address";
    }
    leaf vrf {
      type leafref {
        path "/ac:services/cpedeployment:managed-cpe-services/customer[name=current()/../../../../../../name]/vrfs/vrf/vrf-name";
      }
      description
        "Select Crypto ISAKMP Peer VRF";
      n-ext:maps-to "/ac:devices/ac:device[ac:id=current()/../../../device-ip]/dmvpn:crypto-peers/dmvpn:crypto-peer[address=current()/../peer-address]/vrf-name";
    }
    container set-attributes {
      list attribute {
        key "name";
        leaf name {
          type string-no-space;
          description
            "Enter Crypto ISAKMP Peer Set Attributes Name
             This is an internal field to Anuta NCX";
        }
        leaf attribute-type {
          type enumeration {
            enum "client-endpoint";
            enum "password";
          }
          description
            "Select Aggressive Mode Set Attribute Type";
          //n-ext:maps-to "/ac:devices/ac:device[ac:id=current()/../../../../device-ip]/dmvpn:crypto-peers/dmvpn:crypto-peer/set-attributes/attribute";
        }
        leaf password {
          type string-no-lead-trail-space;
          description
            "Enter Aggressive Mode Password";
          n-ext:maps-to "/ac:devices/ac:device[ac:id=current()/../../../../../device-ip]/dmvpn:crypto-peers/dmvpn:crypto-peer[address=current()/../../../peer-address]/set-attributes[attribute=current()/../attribute-type]/password";
          when "../attribute-type = 'password'";
        }
        leaf endpoint-type {
          type enumeration {
            enum "fqdn";
            enum "ipv4-address";
            enum "user-fqdn";
          }
          description
            "Select Aggressive Mode Attribute Type";
          //n-ext:maps-to "/ac:devices/ac:device[ac:id=current()/../../../../device-ip]/dmvpn:crypto-peers/dmvpn:crypto-peer/set-attributes[attribute=current()/../attribute-type]/endpoint";
          when "../attribute-type = 'client-endpoint'";
        }
        leaf fqdn {
          type string-no-lead-trail-space;
          description
            "Enter Aggressive Mode FQDN";
          n-ext:maps-to "/ac:devices/ac:device[ac:id=current()/../../../../../device-ip]/dmvpn:crypto-peers/dmvpn:crypto-peer[address=current()/../../../peer-address]/set-attributes[attribute=current()/../attribute-type]/fqdn";
          when "../attribute-type = 'client-endpoint' and ../endpoint-type = 'fqdn'";
        }
        leaf ipv4-address {
          type inet:ipv4-address;
          description
            "Enter Aggressive Mode IPv4 Address";
          n-ext:maps-to "/ac:devices/ac:device[ac:id=current()/../../../../../device-ip]/dmvpn:crypto-peers/dmvpn:crypto-peer[address=current()/../../../peer-address]/set-attributes[attribute=current()/../attribute-type]/ipv4-address";
          when "../attribute-type = 'client-endpoint' and ../endpoint-type = 'ipv4-address'";
        }
        leaf user-fqdn {
          type string-no-lead-trail-space;
          description
            "Enter Aggressive Mode User-FQDN";
          n-ext:maps-to "/ac:devices/ac:device[ac:id=current()/../../../../../device-ip]/dmvpn:crypto-peers/dmvpn:crypto-peer[address=current()/../../../peer-address]/set-attributes[attribute=current()/../attribute-type]/user-fqdn";
          when "../attribute-type = 'client-endpoint' and ../endpoint-type = 'user-fqdn'";
        }
      }
    }
  }

  grouping advertise-network-dps {
    leaf name {
      type string;
      description
        "string";
    }
    leaf prefix {
      type inet:ipv4-prefix;
      description
        "Valid IPv4 Prefix (A.B.C.D/Z for e.x: 172.16.1.0/24)";
      mandatory true;
    }
    leaf route-map {
      type leafref {
        path "../../../../../../route-maps/route-map/route-map-name";
      }
      description
        "route-map";
    }
    leaf vrf-name {
      description
        "name";
      type leafref {
        path "../../../../../../vrfs/vrf/vrf-name";
      }
    }
  }

  grouping ospf-network-def {
    leaf name {
      type string-no-space;
      description
        "Enter OSPF Network Name
         This is an internal name for Anuta NCX
        ";
    }
    leaf ospf-id {
      type uint16;
      description
        "Enter OSPF Process ID";
    }
    leaf prefix {
      type inet:ipv4-prefix;
      description
        "Enter OSPF subnet (eg: 10.0.0.0/24)";
      mandatory true;
    }
    leaf area {
      type union {
        type uint32;
        type inet:ipv4-address;
      }
      description
        "Enter OSPF area";
    }
    leaf nssa {
      type boolean;
      description
        "Check to configure area as NSSA";
    }
    leaf vrf-name {
      description
        "Select VRF if OSPF process runs under a VRF";
      type leafref {
        path "../../../../../../vrfs/vrf/vrf-name";
      }
    }
  }

  grouping object-group-def {
    leaf type {
      type enumeration {
        enum "network";
        enum "service";
      }
      description
        "network
         service";
      mandatory true;
      n-ext:maps-to "/ac:devices/ac:device/acl:object-groups-acl/object-group[name=current/../name]/type";
    }
    leaf name {
      type string-no-space;
      description
        "string";
      n-ext:maps-to "/ac:devices/ac:device/acl:object-groups-acl/object-group/name";
    }
    leaf description {
      type string;
      description
        "string";
      n-ext:maps-to "/ac:devices/ac:device/acl:object-groups-acl/object-group[name=current/../name]/description";
    }
    container networks {
      list network {
        key "name";
        uses network-group;
      }
    }
    container services {
      list service {
        key "name";
        uses service-group;
      }
    }
  }

  grouping network-group {
    leaf name {
      type string-no-lead-trail-space;
      description
        "Enter Network Object Group
         This is an internal field to Anuta NCX";
      n-ext:maps-to "/ac:devices/ac:device/acl:object-groups-acl/object-group[name=current()/../../../name]/networks/network/name";
      //n-ext:maps-to "/ac:devices/device/acl:object-groups-acl/object-group/networks/network/name";
    }
    leaf description {
      type string;
      description
        "string";
      config false;
    }
    leaf group-object {
      type string-no-space;
      description
        "Enter Nested Object Group";
      n-ext:maps-to "/ac:devices/ac:device/acl:object-groups-acl/object-group[name=current()/../../../name]/networks/network[name=current()/../name]/group-object";
      //n-ext:maps-to "/ac:devices/device/acl:object-groups-acl/object-group/networks/network/group-object";
    }
    leaf host {
      type string-no-space;
      description
        "string";
      n-ext:maps-to "/ac:devices/ac:device/acl:object-groups-acl/object-group[name=current()/../../../name]/networks/network[name=current()/../name]/host";
      //n-ext:maps-to "/ac:devices/device/acl:object-groups-acl/object-group/networks/network/host";
    }
    leaf prefix {
      //type inet:ipv4-prefix;
      type string-no-space;
      description
        "Valid IPv4 Prefix (A.B.C.D/Z for e.x: 172.16.1.0/24)";
      //n-ext:maps-to "/ac:devices/device/acl:object-groups-acl/object-group[name=current()/../../../name]/networks/network[name=current()/../name]/ip-address";
      //n-ext:maps-to "/ac:devices/device/acl:object-groups-acl/object-group[name=current()/../../../name]/networks/network[name=current()/../name]/netmask";
      n-ext:maps-to "/ac:devices/ac:device/acl:object-groups-acl/object-group[name=current()/../../../name]/networks/network";
      n-ext:prefix-maps-to "ip-address,netmask";
    }
  }

  grouping service-group {
    leaf name {
      type string-no-lead-trail-space;
      description
        "Enter Service Object Group name.
         This is an internal field for Anuta NCX";
    }
    leaf group-object {
      type string-no-space;
      description
        "Enter Nested Group Object";
    }
    leaf protocol-type {
      type enumeration {
        enum "IP-Protocol-Number";
        enum "Protocol-Name";
      }
      description
        "Select Protocol Type for service
         IP-Protocol-Number will allow to enter the IP Protocol Value (eg: 47 for GRE)
         Protocol-Name will allow to enter the protocol name (eg: icmp, tcp, udp)";
    }
    leaf ip-protocol {
      type uint8 {
        range "0..255";
      }
      description
        "Enter IP Protocol Number";
      when "../protocol-type = 'IP-Protocol-Number'";
    }
    leaf protocol-name {
      type enumeration {
        enum "tcp";
        enum "udp";
        enum "tcp-udp";
        enum "ip";
        enum "icmp";
        enum "ospf";
        enum "ahp";
        enum "eigrp";
        enum "esp";
        enum "igmp";
        enum "ipinip";
        enum "nos";
        enum "pim";
      }
      description
        "Select Protocol Name";
      when "../protocol-type = 'Protocol-Name'";
    }
    leaf port-operation {
      type enumeration {
        enum "source";
      }
      description
        "Select to match source traffic direction";
      when "../protocol-name = 'tcp' or ../protocol-name = 'udp' or ../protocol-name = 'tcp-udp'";
    }
    leaf operator {
      type enumeration {
        enum "eq";
        enum "lt";
        enum "gt";
        enum "range";
      }
      description
        "Select Port Operator";
      when "../protocol-name = 'tcp' or ../protocol-name = 'udp' or ../protocol-name = 'tcp-udp'";
    }
    leaf port-number {
      type uint16 {
        range "0..65535";
      }
      description
        "Enter Port Number";
      when "../protocol-name = 'tcp' or ../protocol-name = 'udp' or ../protocol-name = 'tcp-udp'";
    }
    leaf end-port {
      type uint16 {
        range "0..65535";
      }
      description
        "Enter End Port of the range";
      when "../protocol-name = 'tcp' or ../protocol-name = 'udp' or ../protocol-name = 'tcp-udp' and ../operator = 'range'";
    }
  }

  grouping as-path-acl {
    leaf number {
      type uint16 {
        range "1..500";
      }
      n-ext:maps-to "/ac:devices/ac:device/l3features:as-path-acls/as-path-acl/number";
      description
        "1..500";
    }
    leaf condition {
      type enumeration {
        enum "permit";
        enum "deny";
      }
      n-ext:maps-to "/ac:devices/ac:device/l3features:as-path-acls/as-path-acl[number=current()/../number]/condition";
      //n-ext:maps-to "/ac:devices/device/l3features:as-path-acls/as-path-acl/condition";
      description
        "permit
         deny
        ";
    }
    leaf expression {
      type string;
      description
        "string";
      n-ext:maps-to "/ac:devices/ac:device/l3features:as-path-acls/as-path-acl[number=current()/../number]/expression";
      //n-ext:maps-to "/ac:devices/device/l3features:as-path-acls/as-path-acl/expression";
    }
  }

  grouping vrf-def {
    container vrfs {
      //n-ext:ignore-for-brownfield;
      list vrf {
        key "vrf-name";
        leaf vrf-name {
          type string-no-space;
          description
            "string";
          n-ext:maps-to "/ac:devices/ac:device/l3:vrfs/vrf/name";
        }
        leaf description {
          type string;
          description
            "string";
          n-ext:maps-to "/ac:devices/ac:device/l3:vrfs/vrf[name=current()/../vrf-name]/description";
        }
        leaf rd {
          type string-no-space;
          description
            "string";
          n-ext:maps-to "/ac:devices/ac:device/l3:vrfs/vrf[name=current()/../vrf-name]/rd";
        }
        leaf vrf-definition-mode {
          type boolean;
          description
            "vrf-definition-mode: True/False";
          default "false";
          n-ext:maps-to "/ac:devices/ac:device/l3:vrfs/vrf[name=current()/../vrf-name]/vrf-definition-mode";
        }
        list rt-import {
          key "rt-import";
          leaf rt-import {
            type string-no-space;
            description
              "string";
            n-ext:maps-to "/ac:devices/ac:device/l3:vrfs/vrf[name=current()/../../vrf/vrf-name]/rt-import/rt-import";
          }
        }
        list rt-export {
          key "rt-export";
          leaf rt-export {
            type string-no-space;
            description
              "string";
            n-ext:maps-to "/ac:devices/ac:device/l3:vrfs/vrf[name=current()/../../vrf/vrf-name]/rt-export/rt-export";
          }
        }
        list import-map {
          key "import-map";
          leaf import-map {
            type leafref {
              path "/ac:services/cpedeployment:managed-cpe-services/customer[name=current()/../../../../name]/route-maps/route-map/route-map-name";
              require-instance false;
            }
            description
              "string";
            n-ext:maps-to "/ac:devices/ac:device/l3:vrfs/vrf[name=current()/../../vrf/vrf-name]/import-map/import-map";
          }
          leaf ipv4 {
            type boolean;
            description
              "ipv4: True/False";
            n-ext:maps-to "/ac:devices/ac:device/l3:vrfs/vrf[name=current()/../../vrf/vrf-name]/import-map[import-map=current()/../import-map]/ipv4";
          }
          leaf traffic {
            type table-def;
            description
              "multicast
               unicast
              ";
            when " ../ipv4 = 'true' ";
            n-ext:maps-to "/ac:devices/ac:device/l3:vrfs/vrf[name=current()/../../vrf/vrf-name]/import-map[import-map=current()/../import-map]/table";
          }
          leaf upper-limit {
            type uint32 {
              range "1..2147483647";
            }
            description
              "1..2147483647";
            when " ../ipv4 = 'true' ";
            n-ext:maps-to "/ac:devices/ac:device/l3:vrfs/vrf[name=current()/../../vrf/vrf-name]/import-map[import-map=current()/../import-map]/upper-limit";
          }
        }
        list export-map {
          key "export-map";
          leaf export-map {
            type leafref {
              path "/ac:services/cpedeployment:managed-cpe-services/customer[name=current()/../../../../name]/route-maps/route-map/route-map-name";
              require-instance false;
            }
            description
              "string";
            n-ext:maps-to "/ac:devices/ac:device/l3:vrfs/vrf[name=current()/../../vrf/vrf-name]/export-map/export-map";
          }
          leaf ipv4 {
            type boolean;
            description
              "ipv4: True/False";
            n-ext:maps-to "/ac:devices/ac:device/l3:vrfs/vrf[name=current()/../../vrf/vrf-name]/export-map[export-map=current()/../export-map]/ipv4";
          }
          leaf traffic {
            type table-def;
            description
              "multicast
               unicast
              ";
            when " ../ipv4 = 'true' ";
            n-ext:maps-to "/ac:devices/ac:device/l3:vrfs/vrf[name=current()/../../vrf/vrf-name]/export-map[export-map=current()/../export-map]/table";
          }
          leaf upper-limit {
            type uint32 {
              range "1..2147483647";
            }
            description
              "1..2147483647";
            when " ../ipv4 = 'true' ";
            n-ext:maps-to "/ac:devices/ac:device/l3:vrfs/vrf[name=current()/../../vrf/vrf-name]/export-map[export-map=current()/../export-map]/upper-limit";
          }
        }
      }
    }
  }

  grouping wanop-domain-def-type1 {
    uses sm:service-def {
      refine "name" {
        config false;
      }
      refine "service-sequence" {
        config false;
      }
      refine "resource-pool" {
        n-ext-ui:ncx-ext-allowed-vals "/rp:resource-pools/rp:resource-pool[rp:parent-resource-pool=current()/../../../../resource-pool]/rp:name";
        mandatory true;
      }
    }
    leaf single-cpe-sites {
      type leafref {
        path "../../../../single-cpe-site/single-cpe-site-services/site-name";
        require-instance false;
      }
      description
        "type1-sites";
    }
  }

  grouping wanop-domain-def-type2 {
    uses sm:service-def {
      refine "name" {
        config false;
      }
      refine "service-sequence" {
        config false;
      }
      refine "resource-pool" {
        n-ext-ui:ncx-ext-allowed-vals "/rp:resource-pools/rp:resource-pool[rp:parent-resource-pool=current()/../../../../resource-pool]/rp:name";
        mandatory true;
      }
    }
    leaf dual-cpe-sites {
      type leafref {
        path "../../../../dual-cpe-site/dual-cpe-site-services/site-name";
      }
      description
        "dual-cpe-site-services";
    }
  }

  grouping wanop-def {
    container wanop-services {
      n-ext:ignore-for-brownfield;
      container type1-site {
        list type1-site {
          n-ext:ncx-service;
          key "site-name";
          leaf site-name {
            type string-no-space;
            description
              "string";
          }
          leaf show-topology {
            type boolean;
            description
              "show-topology: True/False";
            config false;
            default "true";
          }
          uses wanop-domain-def-type1;
          uses type1-site-def;
        }
      }
      container type2-site {
        list type2-site {
          n-ext:ncx-service;
          key "site-name";
          leaf site-name {
            type string-no-space;
            description
              "string";
          }
          leaf show-topology {
            type boolean;
            description
              "show-topology: True/False";
            config false;
            default "true";
          }
          uses wanop-domain-def-type2;
          uses type2-site-def;
        }
      }
      container type3-site {
        list type3-site {
          n-ext:ncx-service;
          key "site-name";
          leaf site-name {
            type string-no-space;
            description
              "string";
          }
          leaf show-topology {
            type boolean;
            description
              "show-topology: True/False";
            config false;
            default "true";
          }
          uses wanop-domain-def-type2;
          uses type3-site-def;
        }
      }
      container type4-site {
        list type4-site {
          n-ext:ncx-service;
          key "site-name";
          leaf site-name {
            type string-no-space;
            description
              "string";
          }
          leaf show-topology {
            type boolean;
            description
              "show-topology: True/False";
            config false;
            default "true";
          }
          uses wanop-domain-def-type1;
          uses type4-site-def;
        }
      }
      container label-configuration {
        uses label-configuration-def;
      }
      container applications {
        uses application-def;
      }
    }
  }

  grouping type4-site-def {
    container cpe {
      uses cpe:cpe-def {
        refine "internal-id" {
          default "cpe";
          config false;
        }
        refine "sequence-number" {
          default "1";
          config false;
        }
        refine "name" {
          default "cpe";
          config false;
        }
      }
      leaf level {
        type uint8;
        description
          "0..255";
        default "2";
        config false;
      }
    }
    container wan {
      uses enf:external-network-def {
        refine "internal-id" {
          default "wan";
          config false;
        }
        refine "sequence-number" {
          default "2";
          config false;
        }
        refine "resource-id" {
          config false;
        }
        refine "deploy-on" {
          config false;
        }
        refine "name" {
          default "wan";
          config false;
        }
      }
      leaf level {
        type uint8;
        description
          "0..255";
        default "1";
        config false;
      }
    }
    container cpe-wan {
      uses ic:interconnect-def {
        refine "name" {
          default "cpe-wan";
          config false;
        }
        refine "deploy-on" {
          config false;
        }
        refine "interconnect-name" {
          default "cpe-wan";
          config false;
        }
        refine "resource-id" {
          config false;
        }
        refine "sequence-number" {
          default "34";
          config false;
        }
        refine "internal-id" {
          config false;
        }
        refine "type" {
          config false;
        }
      }
      leaf endpoint1 {
        n-ext:end-point;
        type leafref {
          path "../../wan/internal-id";
        }
        description
          "Reference to the endpoint of the interconnect";
        default "wan";
        config false;
      }
      leaf endpoint2 {
        n-ext:end-point;
        type leafref {
          path "../../cpe/internal-id";
        }
        description
          "Reference to the endpoint of the interconnect";
        default "cpe";
        config false;
      }
    }
    container wanop-primary {
      uses wanop:wanoptimizer-def {
        refine "internal-id" {
          default "wanop-primary";
          config false;
        }
        refine "sequence-number" {
          default "3";
          config false;
        }
      }
      leaf level {
        type uint8;
        description
          "0..255";
        default "3";
        config false;
      }
      leaf device-ip {
        type leafref {
          path "/rp:resource-pools/rp:resource-pool[rp:name=current()/../../resource-pool]/rp:device/rp:id";
        }
        description
          "device-ip";
        n-ext-ui:ncx-ext-allowed-vals "/ac:devices/ac:device[ac:device-type='Steelhead WAN Optimizer']/ac:id";
      }
      uses wanop-associated-services;
      container wanop-endpoints {
        uses wanop-ic-local-props-type1;
      }
      container routes {
        uses routes;
      }
    }
    container wanop-secondary {
      uses wanop:wanoptimizer-def {
        refine "internal-id" {
          default "wanop-secondary";
          config false;
        }
        refine "sequence-number" {
          default "4";
          config false;
        }
      }
      leaf level {
        type uint8;
        description
          "0..255";
        default "4";
        config false;
      }
      leaf device-ip {
        type leafref {
          path "/rp:resource-pools/rp:resource-pool[rp:name=current()/../../resource-pool]/rp:device/rp:id";
        }
        description
          "device-ip";
        n-ext-ui:ncx-ext-allowed-vals "/ac:devices/ac:device[ac:device-type='Steelhead WAN Optimizer']/ac:id";
      }
      uses wanop-associated-services;
      container wanop-endpoints {
        uses wanop-ic-local-props-type1;
      }
      container routes {
        uses routes;
      }
    }
    container cpe-wanop {
      uses ic:interconnect-def {
        refine "name" {
          default "cpe-wanop";
          config false;
        }
        refine "deploy-on" {
          config false;
        }
        refine "resource-id" {
          config false;
        }
        refine "interconnect-name" {
          default "cpe-wanop";
          config false;
        }
        refine "sequence-number" {
          default "7";
          config false;
        }
        refine "internal-id" {
          config false;
        }
        refine "type" {
          config false;
        }
      }
      leaf endpoint1 {
        n-ext:end-point;
        type leafref {
          path "../../cpe/internal-id";
        }
        description
          "Reference to the endpoint of the interconnect";
        default "cpe";
        config false;
      }
      leaf endpoint2 {
        n-ext:end-point;
        type leafref {
          path "../../wanop-primary/internal-id";
        }
        description
          "Reference to the endpoint of the interconnect";
        default "wanop-primary";
        config false;
      }
    }
    container wanop-wanop {
      uses ic:interconnect-def {
        refine "name" {
          default "wanop-wanop";
          config false;
        }
        refine "deploy-on" {
          config false;
        }
        refine "resource-id" {
          config false;
        }
        refine "interconnect-name" {
          default "wanop-wanop";
          config false;
        }
        refine "sequence-number" {
          default "7";
          config false;
        }
        refine "internal-id" {
          config false;
        }
        refine "type" {
          config false;
        }
      }
      leaf endpoint1 {
        n-ext:end-point;
        type leafref {
          path "../../wanop-primary/internal-id";
        }
        description
          "Reference to the endpoint of the interconnect";
        default "wanop-primary";
        config false;
      }
      leaf endpoint2 {
        n-ext:end-point;
        type leafref {
          path "../../wanop-secondary/internal-id";
        }
        description
          "Reference to the endpoint of the interconnect";
        default "wanop-secondary";
        config false;
      }
    }
    container lan {
      uses vnf:virtual-network-def {
        refine "internal-id" {
          default "lan";
          config false;
        }
        refine "sequence-number" {
          default "41";
          config false;
        }
        refine "resource-id" {
          config false;
        }
        refine "deploy-on" {
          config false;
        }
        refine "name" {
          default "lan";
          config false;
        }
      }
      leaf level {
        type uint8;
        description
          "0..255";
        default "5";
        config false;
      }
    }
    container wanop-lan {
      uses ic:interconnect-def {
        refine "name" {
          default "wanop-lan";
          config false;
        }
        refine "deploy-on" {
          config false;
        }
        refine "resource-id" {
          config false;
        }
        refine "interconnect-name" {
          default "wanop-lan";
          config false;
        }
        refine "sequence-number" {
          default "6";
          config false;
        }
        refine "internal-id" {
          config false;
        }
        refine "type" {
          config false;
        }
      }
      leaf endpoint1 {
        n-ext:end-point;
        type leafref {
          path "../../wanop-secondary/internal-id";
        }
        description
          "Reference to the endpoint of the interconnect";
        default "wanop-secondary";
        config false;
      }
      leaf endpoint2 {
        n-ext:end-point;
        type leafref {
          path "../../lan/internal-id";
        }
        description
          "Reference to the endpoint of the interconnect";
        default "lan";
        config false;
      }
    }
  }

  grouping type3-site-def {
    container cpe-primary {
      uses cpe:cpe-def {
        refine "internal-id" {
          default "cpe-primary";
          config false;
        }
        refine "sequence-number" {
          default "1";
          config false;
        }
        refine "name" {
          default "cpe-primary";
          config false;
        }
      }
      leaf level {
        type uint8;
        description
          "0..255";
        default "2";
        config false;
      }
    }
    container cpe-secondary {
      uses cpe:cpe-def {
        refine "internal-id" {
          default "cpe-secondary";
          config false;
        }
        refine "sequence-number" {
          default "1";
          config false;
        }
        refine "name" {
          default "cpe-secondary";
          config false;
        }
      }
      leaf level {
        type uint8;
        description
          "0..255";
        default "2";
        config false;
      }
    }
    container cpe-primary-cpe-secondary-ic {
      uses ic:interconnect-def {
        refine "name" {
          default "cpe-primary-cpe-secondary-ic";
          config false;
        }
        refine "deploy-on" {
          config false;
        }
        refine "interconnect-name" {
          default "cpe-primary-cpe-secondary-ic";
          config false;
        }
        refine "resource-id" {
          config false;
        }
        refine "sequence-number" {
          default "30";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../cpe-secondary/internal-id";
        }
        description
          "Reference to the endpoint of the interconnect";
        default "cpe-secondary";
        config false;
      }
    }
    container primary-wan {
      uses enf:external-network-def {
        refine "internal-id" {
          default "primary-wan";
          config false;
        }
        refine "sequence-number" {
          default "2";
          config false;
        }
        refine "resource-id" {
          config false;
        }
        refine "deploy-on" {
          config false;
        }
        refine "name" {
          default "primary-wan";
          config false;
        }
      }
      leaf level {
        type uint8;
        description
          "0..255";
        default "1";
        config false;
      }
    }
    container cpe-primary-wan {
      uses ic:interconnect-def {
        refine "name" {
          default "cpe-primary-wan";
          config false;
        }
        refine "deploy-on" {
          config false;
        }
        refine "interconnect-name" {
          default "cpe-primary-wan";
          config false;
        }
        refine "resource-id" {
          config false;
        }
        refine "sequence-number" {
          default "34";
          config false;
        }
        refine "internal-id" {
          config false;
        }
        refine "type" {
          config false;
        }
      }
      leaf endpoint1 {
        n-ext:end-point;
        type leafref {
          path "../../primary-wan/internal-id";
        }
        description
          "Reference to the endpoint of the interconnect";
        default "primary-wan";
        config false;
      }
      leaf endpoint2 {
        n-ext:end-point;
        type leafref {
          path "../../cpe-primary/internal-id";
        }
        description
          "Reference to the endpoint of the interconnect";
        default "cpe-primary";
        config false;
      }
    }
    container secondary-wan {
      uses enf:external-network-def {
        refine "internal-id" {
          default "secondary-wan";
          config false;
        }
        refine "sequence-number" {
          default "37";
          config false;
        }
        refine "resource-id" {
          config false;
        }
        refine "deploy-on" {
          config false;
        }
        refine "name" {
          default "secondary-wan";
          config false;
        }
      }
      leaf level {
        type uint8;
        description
          "0..255";
        default "1";
        config false;
      }
    }
    container cpe-secondary-wan {
      uses ic:interconnect-def {
        refine "name" {
          default "cpe-secondary-wan";
          config false;
        }
        refine "deploy-on" {
          config false;
        }
        refine "interconnect-name" {
          default "cpe-secondary-wan";
          config false;
        }
        refine "resource-id" {
          config false;
        }
        refine "sequence-number" {
          default "38";
          config false;
        }
        refine "internal-id" {
          config false;
        }
        refine "type" {
          config false;
        }
      }
      leaf endpoint1 {
        n-ext:end-point;
        type leafref {
          path "../../secondary-wan/internal-id";
        }
        description
          "Reference to the endpoint of the interconnect";
        default "secondary-wan";
        config false;
      }
      leaf endpoint2 {
        n-ext:end-point;
        type leafref {
          path "../../cpe-secondary/internal-id";
        }
        description
          "Reference to the endpoint of the interconnect";
        default "cpe-secondary";
        config false;
      }
    }
    container wanop {
      uses wanop:wanoptimizer-def {
        refine "internal-id" {
          default "wanop";
          config false;
        }
        refine "sequence-number" {
          default "4";
          config false;
        }
      }
      leaf level {
        type uint8;
        description
          "0..255";
        default "4";
        config false;
      }
      leaf device-ip {
        type leafref {
          path "/rp:resource-pools/rp:resource-pool[rp:name=current()/../../resource-pool]/rp:device/rp:id";
        }
        description
          "device-ip";
        n-ext-ui:ncx-ext-allowed-vals "/ac:devices/ac:device[ac:device-type='Steelhead WAN Optimizer']/ac:id";
      }
      uses wanop-associated-services;
      container wanop-endpoints {
        uses wanop-ic-local-props-type2;
      }
      container routes {
        uses routes;
      }
    }
    container cpe-wanop {
      uses ic:interconnect-def {
        refine "name" {
          default "cpe-wanop";
          config false;
        }
        refine "deploy-on" {
          config false;
        }
        refine "resource-id" {
          config false;
        }
        refine "interconnect-name" {
          default "cpe-wanop";
          config false;
        }
        refine "sequence-number" {
          default "7";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../wanop/internal-id";
        }
        description
          "Reference to the endpoint of the interconnect";
        default "wanop";
        config false;
      }
      leaf endpoint3 {
        n-ext:end-point;
        type leafref {
          path "../../cpe-secondary/internal-id";
        }
        description
          "Reference to the endpoint of the interconnect";
        default "cpe-secondary";
        config false;
      }
    }
    container lan {
      uses vnf:virtual-network-def {
        refine "internal-id" {
          default "lan";
          config false;
        }
        refine "sequence-number" {
          default "41";
          config false;
        }
        refine "resource-id" {
          config false;
        }
        refine "deploy-on" {
          config false;
        }
        refine "name" {
          default "lan";
          config false;
        }
      }
      leaf level {
        type uint8;
        description
          "0..255";
        default "5";
        config false;
      }
    }
    container wanop-lan {
      uses ic:interconnect-def {
        refine "name" {
          default "wanop-lan";
          config false;
        }
        refine "deploy-on" {
          config false;
        }
        refine "resource-id" {
          config false;
        }
        refine "interconnect-name" {
          default "wanop-lan";
          config false;
        }
        refine "sequence-number" {
          default "6";
          config false;
        }
        refine "internal-id" {
          config false;
        }
        refine "type" {
          config false;
        }
      }
      leaf endpoint1 {
        n-ext:end-point;
        type leafref {
          path "../../wanop/internal-id";
        }
        description
          "Reference to the endpoint of the interconnect";
        default "wanop";
        config false;
      }
      leaf endpoint2 {
        n-ext:end-point;
        type leafref {
          path "../../lan/internal-id";
        }
        description
          "Reference to the endpoint of the interconnect";
        default "lan";
        config false;
      }
    }
  }

  grouping routes {
    list route {
      key "dest-ip-address dest-mask";
      leaf dest-ip-address {
        type inet:ipv4-address;
        description
          "Enter Static Route Destination Subnet";
        n-ext:maps-to "/ac:devices/ac:device/wanop-device:routes/route/dest-ip-address";
      }
      leaf dest-mask {
        type inet:ipv4-address;
        description
          "Enter Static Route Destination Subnet Mask";
        n-ext:maps-to "/ac:devices/ac:device/wanop-device:routes/route/dest-mask";
      }
      list options {
        key "id";
        leaf id {
          type string;
          description
            "Enter Static Route ID
             This is an internal field for Anuta NCX to differentiate static route options
            ";
          n-ext:maps-to "/ac:devices/ac:device/wanop-device:routes/route/options/id";
        }
        leaf next-hop-ip {
          type string;
          description
            "Enter Static Route Next-Hop IP";
          n-ext:maps-to "/ac:devices/ac:device/wanop-device:routes/route/options/next-hop-ip";
        }
        leaf inpath-route {
          type boolean;
          description
            "Enter WANOp Inpath Route";
        }
        leaf interface-name {
          type leafref {
            path "/ac:devices/ac:device[ac:id=current()/../../../../device-ip]/if:interfaces/if:interface/if:long-name";
          }
          description
            "Select Interface Name";
          n-ext:maps-to "/ac:devices/ac:device/wanop-device:routes/route/options/interface-name";
        }
      }
    }
  }

  grouping inpath-rules-def {
    list inpath-rules {
      key "rulenum";
      leaf rule-type {
        type enumeration {
          enum "auto-discover";
          enum "pass-through";
          enum "discard";
          enum "deny";
          enum "fixed-target";
        }
        description
          "auto-discover
           pass-through
           discard
           deny
           fixed-target
          ";
        n-ext:maps-to "/ac:devices/ac:device/wanop-device:inpath-rules/inpath-rules-def/rule-type";
      }
      leaf packet-mode-uni {
        type enumeration {
          enum "packet-mode-uni";
        }
        description
          "packet-mode-uni\n";
        when "../rule-type = 'fixed-target'";
        n-ext:maps-to "/ac:devices/ac:device/wanop-device:inpath-rules/inpath-rules-def/packet-mode-uni";
      }
      leaf srcaddr {
        type union {
          type inet:ipv4-prefix;
          type enumeration {
            enum "all-ip";
            enum "all-ipv4";
            enum "all-ipv6";
          }
        }
        description
          "Union Input types:
           inet:ip-address
           enumeration
          ";
        n-ext:maps-to "/ac:devices/ac:device/wanop-device:inpath-rules/inpath-rules-def/srcaddr";
      }
      leaf srcport {
        type union {
          type string;
          type leafref {
            path "../../../../../../label-configuration/port-labels/port-label/port-label-name";
            require-instance false;
          }
        }
        description
          "Union Input types:
           string
           leafref
          ";
        when "../packet-mode-uni = 'packet-mode-uni' or ../rule-type = 'pass-through'";
        n-ext:maps-to "/ac:devices/ac:device/wanop-device:inpath-rules/inpath-rules-def/srcport";
      }
      leaf dstaddr {
        type union {
          type inet:ipv4-prefix;
          type enumeration {
            enum "all-ip";
            enum "all-ipv4";
            enum "all-ipv6";
          }
        }
        description
          "Union Input types:
           inet:ip-address
           enumeration
          ";
        n-ext:maps-to "/ac:devices/ac:device/wanop-device:inpath-rules/inpath-rules-def/dstaddr";
      }
      leaf dstport {
        type union {
          type string;
          type leafref {
            path "../../../../../../label-configuration/port-labels/port-label/port-label-name";
            require-instance false;
          }
        }
        description
          "Union Input types:
           string
           leafref
          ";
        n-ext:maps-to "/ac:devices/ac:device/wanop-device:inpath-rules/inpath-rules-def/dstport";
      }
      leaf dst-domain {
        type leafref {
          path "../../../../../../label-configuration/domain-labels/domain-label/domain-label-name";
          require-instance false;
        }
        description
          "dst-domain";
        when "../rule-type = 'fixed-target' and ../packet-mode-uni != 'packet-mode-uni' or ../rule-type = 'auto-discover' or ../rule-type = 'pass-through'";
        n-ext:maps-to "/ac:devices/ac:device/wanop-device:inpath-rules/inpath-rules-def/dst-domain";
      }
      leaf dst-host {
        type leafref {
          path "../../../../../../label-configuration/host-labels/host-label/host-label-name";
        }
        description
          "dst-host";
        when "../rule-type = 'fixed-target' and ../packet-mode-uni != 'packet-mode-uni' or ../rule-type = 'auto-discover' or ../rule-type = 'pass-through'";
        n-ext:maps-to "/ac:devices/ac:device/wanop-device:inpath-rules/inpath-rules-def/dst-host";
      }
      leaf optimization {
        type enumeration {
          enum "normal";
          enum "sdr-only";
          enum "sdr-m";
          enum "compr-only";
          enum "none";
        }
        description
          "normal - Performs LZ compression and SDR. This is the default optimization policy.
           sdr-only - Turns off LZ compression.
           sdr-m - Performs data reduction entirely in memory, which prevents the SteelHead from reading and writing to and from the disk.
           compr-only - Turns off SDR but perform LZ compression.
           none - Turns off LZ compression and SDR.";
        when "../rule-type = 'auto-discover' or ../rule-type = 'fixed-target'";
        n-ext:maps-to "/ac:devices/ac:device/wanop-device:inpath-rules/inpath-rules-def/optimization";
      }
      leaf preoptimization {
        type enumeration {
          enum "ssl";
          enum "oracle-forms";
          enum "oracle-forms+ssl";
          enum "none";
        }
        description
          "enum ssl - Enables SSL preoptimization processing for traffic via SSL secure ports.
           enum oracle-forms - Enables preoptimization processing for the Oracle Forms browser plug-in. This policy is not compatible with IPv6.
           enum oracle-forms+ssl - Enables preoptimization processing for both the Oracle Forms browser plug-in and SSL encrypted traffic through SSL secure ports on the client-side SteelHead. This policy is not compatible with IPv6.
           enum none - If SSL or Oracle Forms preoptimization processing is turned on and you want to turn it off for a port, specify none.";
        when " ../rule-type = 'fixed-target' and ../packet-mode-uni != 'packet-mode-uni' or ../rule-type = 'auto-discover'";
        n-ext:maps-to "/ac:devices/ac:device/wanop-device:inpath-rules/inpath-rules-def/preoptimization";
      }
      leaf latency-opt {
        type enumeration {
          enum "citrix";
          enum "http";
          enum "normal";
          enum "outlook-anywhr";
          enum "exchange-auto";
          enum "none";
        }
        description
          "citrix - Always uses Citrix optimization on connections matching this rule.
           http - Performs HTTP optimization on connections matching this rule.
           normal - Performs HTTP optimization on ports 80, 8080, and (with SSL preoptimization) 443.
           outlook-anywhr - Always uses Outlook-Anywhere optimization on the connection.
           exchange-auto - Automatically detects MAPI transport protocols (Autodiscover, Outlook Anywhere, and MAPI over HTTP) and HTTP traffic.
           none - Does not perform latency optimization on connections matching this rule.";
        when "../rule-type = 'fixed-target' and ../packet-mode-uni != 'packet-mode-uni' or ../rule-type = 'auto-discover'";
        n-ext:maps-to "/ac:devices/ac:device/wanop-device:inpath-rules/inpath-rules-def/latency-opt";
      }
      leaf vlan {
        type int16 {
          range "-1..4096";
        }
        description
          "VLAN Tag ID (1-4094, 0 for untagged, or -1 for all)";
        n-ext:maps-to "/ac:devices/ac:device/wanop-device:inpath-rules/inpath-rules-def/vlan";
      }
      leaf neural-mode {
        type enumeration {
          enum "always";
          enum "dynamic";
          enum "never";
          enum "tcphints";
        }
        description
          "always
           dynamic
           never
           tcphints
          ";
        when " ../rule-type = 'fixed-target' and ../packet-mode-uni != 'packet-mode-uni' or ../rule-type = 'auto-discover'";
        n-ext:maps-to "/ac:devices/ac:device/wanop-device:inpath-rules/inpath-rules-def/neural-mode";
      }
      leaf cloud-accel {
        type enumeration {
          enum "auto";
          enum "passthru";
        }
        description
          "auto
           passthru
          ";
        when "../rule-type = 'auto-discover' or ../rule-type = 'pass-through'";
        n-ext:maps-to "/ac:devices/ac:device/wanop-device:inpath-rules/inpath-rules-def/cloud-accel";
      }
      leaf web-proxy {
        type enumeration {
          enum "auto";
          enum "force";
          enum "none";
        }
        description
          "auto
           force
           none
          ";
        when "../rule-type = 'auto-discover' or ../rule-type = 'pass-through'";
        n-ext:maps-to "/ac:devices/ac:device/wanop-device:inpath-rules/inpath-rules-def/web-proxy";
      }
      leaf wan-visibility {
        type enumeration {
          enum "correct";
          enum "port";
          enum "full wan-vis-opt fwd-reset";
          enum "full none";
        }
        description
          "correct
           port
           full wan-vis-opt fwd-reset
           full none
          ";
        when "../rule-type = 'auto-discover'";
        n-ext:maps-to "/ac:devices/ac:device/wanop-device:inpath-rules/inpath-rules-def/wan-visibility";
      }
      leaf wan-vis-opt {
        type enumeration {
          enum "fwd-reset";
          enum "none";
        }
        description
          "fwd-reset
           none
          ";
        when "../rule-type = 'auto-discover'";
        n-ext:maps-to "/ac:devices/ac:device/wanop-device:inpath-rules/inpath-rules-def/wan-vis-opt";
      }
      leaf description {
        type string;
        description
          "string";
        n-ext:maps-to "/ac:devices/ac:device/wanop-device:inpath-rules/inpath-rules-def/description";
      }
      leaf auto-kickoff {
        type enumeration {
          enum "enable";
          enum "disable";
        }
        description
          "Enable/disable auto-kichoff";
        when "../rule-type = 'fixed-target' and ../packet-mode-uni != 'packet-mode-uni' or ../rule-type = 'auto-discover'";
        n-ext:maps-to "/ac:devices/ac:device/wanop-device:inpath-rules/inpath-rules-def/auto-kickoff";
      }
      leaf rule-enable {
        type boolean;
        description
          "Enable rule: True/False";
        n-ext:maps-to "/ac:devices/ac:device/wanop-device:inpath-rules/inpath-rules-def/rule-enable";
      }
      leaf rulenum {
        type uint8;
        description
          "The rule is inserted into the list at the specified position.";
        n-ext:maps-to "/ac:devices/ac:device/wanop-device:inpath-rules/inpath-rules-def/rulenum";
      }
      leaf protocol {
        type union {
          type string;
          type enumeration {
            enum "tcp";
            enum "udp";
            enum "Any";
          }
        }
        description
          "Union Input types:
           string
           enumeration
          ";
        //when packet-mode-uni==true
        when "../rule-type = 'pass-through' or ../packet-mode-uni = 'packet-mode-uni'";
        n-ext:maps-to "/ac:devices/ac:device/wanop-device:inpath-rules/inpath-rules-def/protocol";
      }
      leaf target-addr {
        type union {
          type inet:ip-address;
          type enumeration {
            enum "all-ip";
            enum "all-ipv4";
            enum "all-ipv6";
          }
        }
        description
          "Union Input types:
           inet:ip-address
           enumeration
          ";
        mandatory true;
        when "../rule-type = 'fixed-target'";
        n-ext:maps-to "/ac:devices/ac:device/wanop-device:inpath-rules/inpath-rules-def/target-addr";
      }
      leaf target-port {
        type union {
          type string;
          type leafref {
            path "../../../../../../label-configuration/port-labels/port-label/port-label-name";
            require-instance false;
          }
        }
        description
          "Union Input types:
           string
           leafref
          ";
        when "../rule-type = 'fixed-target'";
        n-ext:maps-to "/ac:devices/ac:device/wanop-device:inpath-rules/inpath-rules-def/target-port";
      }
      leaf backup-addr {
        type inet:ip-address;
        description
          "Valid IPv4/v6 Address (A.B.C.D for e.x: 172.16.1.1 or X::Y for e.x: 2001::1)";
        when "../rule-type = 'fixed-target'";
        n-ext:maps-to "/ac:devices/ac:device/wanop-device:inpath-rules/inpath-rules-def/backup-addr";
      }
      leaf backup-port {
        type union {
          type string;
          type leafref {
            path "../../../../../../label-configuration/port-labels/port-label/port-label-name";
            require-instance false;
          }
        }
        description
          "Union Input types:
           string
           leafref
          ";
        when "../rule-type = 'fixed-target'";
        n-ext:maps-to "/ac:devices/ac:device/wanop-device:inpath-rules/inpath-rules-def/backup-port";
      }
    }
    list move-rule {
      key "id";
      leaf id {
        type string;
        description
          "info/description of move-rule or any unique-value as id";
      }
      leaf from-rule-num {
        type leafref {
          path "../../inpath-rules/rulenum";
        }
        description
          "from-rule-num";
        mandatory true;
        n-ext:maps-to "/ac:devices/ac:device/wanop-device:inpath-rules/move-rule/from-rule-num";
      }
      leaf to-rule-num {
        type leafref {
          path "../../inpath-rules/rulenum";
        }
        description
          "to-rule-num";
        mandatory true;
        n-ext:maps-to "/ac:devices/ac:device/wanop-device:inpath-rules/move-rule/to-rule-num";
      }
    }
  }

  grouping application-def {
    list application {
      key "application-name";
      leaf application-name {
        type string;
        description
          "string";
        mandatory true;
        n-ext:maps-to "/ac:devices/ac:device/wanop-device:wanop-applications/wanop-application/name";
      }
      leaf group {
        type enumeration {
          enum "Business Bulk";
          enum "Business Critical";
          enum "Business Productivity";
          enum "Business Standard";
          enum "Business VDI";
          enum "Business Video";
          enum "Business Voice";
          enum "Recreational";
          enum "Standard Bulk";
          enum "Custom Applications";
        }
        description
          "Business Bulk
           Business Critical
           Business Productivity
           Business Standard
           Business VDI
           Business Video
           Business Voice
           Recreational
           Standard Bulk
           Custom Applications
          ";
        n-ext:maps-to "/ac:devices/ac:device/wanop-device:wanop-applications/wanop-application/group";
      }
      leaf business-crit {
        type enumeration {
          enum "Lowest Criticality";
          enum "Low Criticality";
          enum "Medium Criticality";
          enum "High Criticality";
          enum "Highest Criticality";
        }
        description
          "Lowest Criticality
           Low Criticality
           Medium Criticality
           High Criticality
           Highest Criticality
          ";
        n-ext:maps-to "/ac:devices/ac:device/wanop-device:wanop-applications/wanop-application/business-crit";
      }
      leaf category {
        type enumeration {
          enum "Collaboration";
          enum "Database";
          enum "File Transfer";
          enum "Games";
          enum "Mail";
          enum "Messaging";
          enum "Network Monitoring";
          enum "Networking";
          enum "Proxy";
          enum "Remote Access";
          enum "Social Networking";
          enum "Streaming Media";
          enum "VPN and Tunneling";
          enum "Web Services";
          enum "Other";
        }
        description
          "Collaboration
           Database
           File Transfer
           Games
           Mail
           Messaging
           Network Monitoring
           Networking
           Proxy
           Remote Access
           Social Networking
           Streaming Media
           VPN and Tunneling
           Web Services
           Other
          ";
        n-ext:maps-to "/ac:devices/ac:device/wanop-device:wanop-applications/wanop-application/category";
      }
      leaf description {
        type string;
        description
          "string";
        n-ext:maps-to "/ac:devices/ac:device/wanop-device:wanop-applications/wanop-application/description";
      }
      leaf traffic-type {
        type enumeration {
          enum "Any";
          enum "Optimized";
          enum "Passthrough";
        }
        description
          "Any
           Optimized
           Passthrough
          ";
        n-ext:maps-to "/ac:devices/ac:device/wanop-device:wanop-applications/wanop-application/traffic-type";
      }
      leaf transport-prot {
        type union {
          type string;
          type enumeration {
            enum "Any";
            enum "HOPOPT";
            enum "ICMP";
            enum "IGMP";
            enum "GGP";
            enum "IPv4";
            enum "ST";
            enum "TCP";
            enum "CBT";
            enum "EGP";
            enum "IGP";
            enum "BBN-RCC-MON";
            enum "NVP-II";
            enum "PUP";
            enum "ARGUS";
            enum "EMCON";
            enum "XNET";
            enum "CHAOS";
            enum "UDP";
            enum "MUX";
            enum "DCN-MEAS";
            enum "HMP";
            enum "PRM";
            enum "XNS-IDP";
            enum "TRUNK-1";
            enum "TRUNK-2";
            enum "LEAF-1";
            enum "LEAF-2";
            enum "RDP";
            enum "IRTP";
            enum "ISO-TP4";
            enum "NET-BLT";
            enum "MFE-NSP";
            enum "MERIT-INP";
            enum "DCCP";
            enum "3PC";
            enum "IDPR";
            enum "XTP";
            enum "DDP";
            enum "IDPR-CMTP";
            enum "TP++";
            enum "IL";
            enum "IPv6";
            enum "SDRP";
            enum "IPv6-Route";
            enum "IPv6-Frag";
            enum "IDRP";
            enum "RSVP";
            enum "GRE";
            enum "DSR";
            enum "BNA";
            enum "IPsec ESP";
            enum "IPsec AH";
            enum "I-NLSP";
            enum "SWIPE";
            enum "NARP";
            enum "MOBILE";
            enum "TLSP";
            enum "SKIP";
            enum "IPv6-ICMP";
            enum "IPv6-NoNxt";
            enum "IPv6-Opts";
            enum "CFTP";
            enum "SAT-EXPAK";
            enum "KRYPTOLAN";
            enum "RVB";
            enum "IPPC";
            enum "SAT-MON";
            enum "VISA";
            enum "IPCV";
            enum "CPNX";
            enum "CPHB";
            enum "WSN";
            enum "PVP";
            enum "BR-SAT-MON";
            enum "SUN-ND";
            enum "WB-MON";
            enum "WB-EXPAK";
            enum "ISO-IP";
            enum "VMTP";
            enum "SECURE-VMTP";
            enum "VINES";
            enum "TTP";
            enum "NSFNET-IGP";
            enum "DGP";
            enum "TCF";
            enum "EIGRP";
            enum "OSPFIGP";
            enum "Sprite-RPC";
            enum "LARP";
            enum "MTP";
            enum "AX.25";
            enum "IPIP";
            enum "MICP";
            enum "SSC-SP";
            enum "ETHERIP";
            enum "ENCAP";
            enum "GMTP";
            enum "IFNP";
            enum "PNNI";
            enum "PIM";
            enum "ARIS";
            enum "SCPS";
            enum "QNX";
            enum "A/N";
            enum "IPComp";
            enum "SNP";
            enum "Compaq-Peer";
            enum "IPX-in-IP";
            enum "VRRP";
            enum "PGM";
            enum "L2TP";
            enum "DDX";
            enum "IATP";
            enum "STP";
            enum "SRP";
            enum "UTI";
            enum "SMP";
            enum "SM";
            enum "PTP";
            enum "ISIS over IPv4";
            enum "FIRE";
            enum "CRTP";
            enum "CRUDP";
            enum "SSCOPMCE";
            enum "IPLT";
            enum "SPS";
            enum "PIPE";
            enum "SCTP";
            enum "FC";
            enum "RSVP-E2E-IGNORE";
            enum "Mobility Header";
            enum "UDPLite";
            enum "MPLS-in-IP";
            enum "manet";
            enum "HIP";
            enum "Shim6";
            enum "WESP";
            enum "ROHC";
          }
        }
        description
          "Union Input types:
           string
           enumeration
          ";
        n-ext:maps-to "/ac:devices/ac:device/wanop-device:wanop-applications/wanop-application/transport-prot";
      }
      leaf dscp {
        type union {
          type uint8 {
            range "0..63";
          }
          type enumeration {
            enum "Any";
          }
        }
        description
          "Union Input types:
           uint8
           enumeration
          ";
        n-ext:maps-to "/ac:devices/ac:device/wanop-device:wanop-applications/wanop-application/dscp";
      }
      leaf vlan {
        type union {
          type uint16 {
            range "0..4094";
          }
          type enumeration {
            enum "Any";
          }
        }
        description
          "Union Input types:
           uint16
           enumeration
          ";
        n-ext:maps-to "/ac:devices/ac:device/wanop-device:wanop-applications/wanop-application/vlan";
      }
      leaf local-port {
        type union {
          type string;
          type leafref {
            path "../../../label-configuration/port-labels/port-label/port-label-name";
            require-instance false;
          }
        }
        n-ext:maps-to "/ac:devices/ac:device/wanop-device:wanop-applications/wanop-application/local-port";
        description
          "Local port or portlabel of traffic to match";
      }
      leaf remote-port {
        type union {
          type string;
          type leafref {
            path "../../../label-configuration/port-labels/port-label/port-label-name";
            require-instance false;
          }
        }
        n-ext:maps-to "/ac:devices/ac:device/wanop-device:wanop-applications/wanop-application/remote-port";
        description
          "Remote port or portlabel of traffic to match";
      }
      leaf local-net {
        type union {
          type leafref {
            path "../../../label-configuration/host-labels/host-label/host-label-name";
            require-instance false;
          }
          type string;
        }
        n-ext:maps-to "/ac:devices/ac:device/wanop-device:wanop-applications/wanop-application/local-net";
        description
          " Local subnet or hostlabel of traffic to match";
      }
      leaf remote-net {
        type union {
          type leafref {
            path "../../../label-configuration/host-labels/host-label/host-label-name";
            require-instance false;
          }
          type string;
        }
        n-ext:maps-to "/ac:devices/ac:device/wanop-device:wanop-applications/wanop-application/remote-net";
        description
          " Local subnet or hostlabel of traffic to match";
      }
      leaf app-prot {
        type union {
          type string;
          type enumeration {
            enum "Any";
          }
        }
        description
          "Union Input types:
           string
           enumeration
          ";
        n-ext:maps-to "/ac:devices/ac:device/wanop-device:wanop-applications/wanop-application/app-prot";
      }
    }
    list update-application {
      n-ext:ignore-for-brownfield;
      key "id";
      leaf id {
        type string;
        description
          "info/description of application or any unique-value as id";
      }
      leaf application-name {
        type leafref {
          path "../../application/application-name";
        }
        description
          "string";
        mandatory true;
        //n-ext:maps-to "/ac:devices/device/wanop-device:wanop-applications/wanop-application/name";
      }
      leaf group {
        type enumeration {
          enum "Business Bulk";
          enum "Business Critical";
          enum "Business Productivity";
          enum "Business Standard";
          enum "Business VDI";
          enum "Business Video";
          enum "Business Voice";
          enum "Recreational";
          enum "Standard Bulk";
          enum "Custom Applications";
        }
        description
          "Business Bulk
           Business Critical
           Business Productivity
           Business Standard
           Business VDI
           Business Video
           Business Voice
           Recreational
           Standard Bulk
           Custom Applications
          ";
        //n-ext:maps-to "/ac:devices/device/wanop-device:wanop-applications/wanop-application/group";
      }
      leaf business-crit {
        type enumeration {
          enum "Lowest Criticality";
          enum "Low Criticality";
          enum "Medium Criticality";
          enum "High Criticality";
          enum "Highest Criticality";
        }
        description
          "Lowest Criticality
           Low Criticality
           Medium Criticality
           High Criticality
           Highest Criticality
          ";
        //n-ext:maps-to "/ac:devices/device/wanop-device:wanop-applications/wanop-application/business-crit";
      }
      leaf category {
        type enumeration {
          enum "Collaboration";
          enum "Database";
          enum "File Transfer";
          enum "Games";
          enum "Mail";
          enum "Messaging";
          enum "Network Monitoring";
          enum "Networking";
          enum "Proxy";
          enum "Remote Access";
          enum "Social Networking";
          enum "Streaming Media";
          enum "VPN and Tunneling";
          enum "Web Services";
          enum "Other";
        }
        description
          "Collaboration
           Database
           File Transfer
           Games
           Mail
           Messaging
           Network Monitoring
           Networking
           Proxy
           Remote Access
           Social Networking
           Streaming Media
           VPN and Tunneling
           Web Services
           Other
          ";
        //n-ext:maps-to "/ac:devices/device/wanop-device:wanop-applications/wanop-application/category";
      }
      leaf description {
        type string;
        description
          "string";
      }
      leaf traffic-type {
        type enumeration {
          enum "Any";
          enum "Optimized";
          enum "Passthrough";
        }
        description
          "Any
           Optimized
           Passthrough
          ";
        //n-ext:maps-to "/ac:devices/device/wanop-device:wanop-applications/wanop-application/traffic-type";
      }
      leaf transport-prot {
        type union {
          type string;
          type enumeration {
            enum "Any";
            enum "HOPOPT";
            enum "ICMP";
            enum "IGMP";
            enum "GGP";
            enum "IPv4";
            enum "ST";
            enum "TCP";
            enum "CBT";
            enum "EGP";
            enum "IGP";
            enum "BBN-RCC-MON";
            enum "NVP-II";
            enum "PUP";
            enum "ARGUS";
            enum "EMCON";
            enum "XNET";
            enum "CHAOS";
            enum "UDP";
            enum "MUX";
            enum "DCN-MEAS";
            enum "HMP";
            enum "PRM";
            enum "XNS-IDP";
            enum "TRUNK-1";
            enum "TRUNK-2";
            enum "LEAF-1";
            enum "LEAF-2";
            enum "RDP";
            enum "IRTP";
            enum "ISO-TP4";
            enum "NET-BLT";
            enum "MFE-NSP";
            enum "MERIT-INP";
            enum "DCCP";
            enum "3PC";
            enum "IDPR";
            enum "XTP";
            enum "DDP";
            enum "IDPR-CMTP";
            enum "TP++";
            enum "IL";
            enum "IPv6";
            enum "SDRP";
            enum "IPv6-Route";
            enum "IPv6-Frag";
            enum "IDRP";
            enum "RSVP";
            enum "GRE";
            enum "DSR";
            enum "BNA";
            enum "IPsecESP";
            enum "IPsecAH";
            enum "I-NLSP";
            enum "SWIPE";
            enum "NARP";
            enum "MOBILE";
            enum "TLSP";
            enum "SKIP";
            enum "IPv6-ICMP";
            enum "IPv6-NoNxt";
            enum "IPv6-Opts";
            enum "CFTP";
            enum "SAT-EXPAK";
            enum "KRYPTOLAN";
            enum "RVB";
            enum "IPPC";
            enum "SAT-MON";
            enum "VISA";
            enum "IPCV";
            enum "CPNX";
            enum "CPHB";
            enum "WSN";
            enum "PVP";
            enum "BR-SAT-MON";
            enum "SUN-ND";
            enum "WB-MON";
            enum "WB-EXPAK";
            enum "ISO-IP";
            enum "VMTP";
            enum "SECURE-VMTP";
            enum "VINES";
            enum "TTP";
            enum "NSFNET-IGP";
            enum "DGP";
            enum "TCF";
            enum "EIGRP";
            enum "OSPFIGP";
            enum "Sprite-RPC";
            enum "LARP";
            enum "MTP";
            enum "AX.25";
            enum "IPIP";
            enum "MICP";
            enum "SSC-SP";
            enum "ETHERIP";
            enum "ENCAP";
            enum "GMTP";
            enum "IFNP";
            enum "PNNI";
            enum "PIM";
            enum "ARIS";
            enum "SCPS";
            enum "QNX";
            enum "A/N";
            enum "IPComp";
            enum "SNP";
            enum "Compaq-Peer";
            enum "IPX-in-IP";
            enum "VRRP";
            enum "PGM";
            enum "L2TP";
            enum "DDX";
            enum "IATP";
            enum "STP";
            enum "SRP";
            enum "UTI";
            enum "SMP";
            enum "SM";
            enum "PTP";
            enum "ISIS over IPv4";
            enum "FIRE";
            enum "CRTP";
            enum "CRUDP";
            enum "SSCOPMCE";
            enum "IPLT";
            enum "SPS";
            enum "PIPE";
            enum "SCTP";
            enum "FC";
            enum "RSVP-E2E-IGNORE";
            enum "Mobility Header";
            enum "UDPLite";
            enum "MPLS-in-IP";
            enum "manet";
            enum "HIP";
            enum "Shim6";
            enum "WESP";
            enum "ROHC";
          }
        }
        description
          "Union Input types:
           string
           enumeration
          ";
        n-ext:maps-to "/ac:devices/ac:device/wanop-device:wanop-applications/wanop-application/transport-prot";
      }
      leaf dscp {
        type union {
          type uint8 {
            range "0..63";
          }
          type enumeration {
            enum "Any";
          }
        }
        description
          "Union Input types:
           uint8
           enumeration
          ";
        n-ext:maps-to "/ac:devices/ac:device/wanop-device:wanop-applications/wanop-application/dscp";
      }
      leaf vlan {
        type union {
          type uint16 {
            range "0..4094";
          }
          type enumeration {
            enum "Any";
          }
        }
        description
          "Union Input types:
           uint16
           enumeration
          ";
        n-ext:maps-to "/ac:devices/ac:device/wanop-device:wanop-applications/wanop-application/vlan";
      }
      leaf local-port {
        type union {
          type string;
          type leafref {
            path "../../../label-configuration/port-labels/port-label/port-label-name";
            require-instance false;
          }
        }
        //n-ext:maps-to "/ac:devices/device/wanop-device:wanop-applications/wanop-application/local-port";
        description
          "Local port or portlabel of traffic to match";
      }
      leaf remote-port {
        type union {
          type string;
          type leafref {
            path "../../../label-configuration/port-labels/port-label/port-label-name";
            require-instance false;
          }
        }
        //n-ext:maps-to "/ac:devices/device/wanop-device:wanop-applications/wanop-application/remote-port";
        description
          "Remote port or portlabel of traffic to match";
      }
      leaf local-net {
        type union {
          type leafref {
            path "../../../label-configuration/host-labels/host-label/host-label-name";
            require-instance false;
          }
          type string;
        }
        //n-ext:maps-to "/ac:devices/device/wanop-device:wanop-applications/wanop-application/local-net";
        description
          " Local subnet or hostlabel of traffic to match";
      }
      leaf remote-net {
        type union {
          type leafref {
            path "../../../label-configuration/host-labels/host-label/host-label-name";
            require-instance false;
          }
          type string;
        }
        //n-ext:maps-to "/ac:devices/device/wanop-device:wanop-applications/wanop-application/remote-net";
        description
          " Local subnet or hostlabel of traffic to match";
      }
      leaf app-prot {
        type union {
          type string;
          type enumeration {
            enum "Any";
          }
        }
        description
          "Union Input types:
           string
           enumeration
          ";
        n-ext:maps-to "/ac:devices/ac:device/wanop-device:wanop-applications/wanop-application/app-prot";
      }
      leaf operation {
        type operation-def;
        description
          "CREATE
           DELETE
          ";
      }
      leaf type1-site {
        type boolean;
        description
          "type1-site: True/False";
      }
      leaf-list type1-sites {
        type leafref {
          path "../../../type1-site/type1-site/site-name";
          require-instance false;
        }
        //n-ext:maps-to "../../../type1-site/type1-site/site-name";
        description
          "type1-sites";
        when " ../type1-site = 'true' ";
      }
      leaf type2-site {
        type boolean;
        description
          "type2-site: True/False";
      }
      leaf-list type2-sites {
        type leafref {
          path "../../../type2-site/type2-site/site-name";
          require-instance false;
        }
        //n-ext:maps-to "../../../type2-site/type2-site/site-name";
        description
          "type2-sites";
        when " ../type2-site = 'true' ";
      }
      leaf type3-site {
        type boolean;
        description
          "type3-site: True/False";
      }
      leaf-list type3-sites {
        type leafref {
          path "../../../type3-site/type3-site/site-name";
          require-instance false;
        }
        //n-ext:maps-to "../../../type3-site/type3-site/site-name";
        description
          "type3-sites";
        when " ../type3-site = 'true' ";
      }
      leaf type4-site {
        type boolean;
        description
          "type4-site: True/False";
      }
      leaf-list type4-sites {
        type leafref {
          path "../../../type4-site/type4-site/site-name";
          require-instance false;
        }
        //n-ext:maps-to "../../../type4-site/type4-site/site-name";
        description
          "type4-sites";
        when " ../type4-site = 'true' ";
      }
    }
  }

  grouping label-configuration-def {
    container host-labels {
      list host-label {
        key "host-label-name";
        leaf host-label-name {
          type string;
          description
            "string";
          mandatory true;
          n-ext:maps-to "/ac:devices/ac:device/wanop-device:label-configuration/host-label/host-label-name";
        }
        container hostname {
          leaf hostname {
            type string;
            description
              "Comma separated hostname Eg:<hostname or 'hostname, ...'>";
            n-ext:maps-to "/ac:devices/ac:device/wanop-device:label-configuration/host-label/hostname/hostname";
          }
        }
        container subnet {
          leaf subnet {
            type string;
            description
              "Comma separated networks Eg:<network or 'network, ...'>  IPv4 subnet (ie. X.X.X.X/<0-32>)";
            n-ext:maps-to "/ac:devices/ac:device/wanop-device:label-configuration/host-label/subnet/subnet";
          }
        }
      }
      list update-host-label {
        n-ext:ignore-for-brownfield;
        key "id";
        leaf id {
          type string;
          description
            "info/description of host-label or any unique-value as id";
        }
        leaf host-label-name {
          type leafref {
            path "../../host-label/host-label-name";
          }
          description
            "string";
          mandatory true;
          //n-ext:maps-to "/ac:devices/device/wanop-device:label-configuration/host-label/host-label-name";
        }
        leaf hostname {
          type string;
          description
            "Comma separated hostname Eg:<hostname or 'hostname, ...'>";
          //n-ext:maps-to "/ac:devices/device/wanop-device:label-configuration/host-label/hostname/hostname";
        }
        leaf subnet {
          type string;
          description
            "Comma separated networks Eg:<network or 'network, ...'>  IPv4 subnet (ie. X.X.X.X/<0-32>)";
          //n-ext:maps-to "/ac:devices/device/wanop-device:label-configuration/host-label/subnet/subnet";
        }
        leaf operation {
          type operation-def;
          description
            "CREATE
             DELETE
            ";
        }
        leaf type1-site {
          type boolean;
          description
            "type1-site: True/False";
        }
        leaf-list type1-sites {
          type leafref {
            path "../../../../type1-site/type1-site/site-name";
            require-instance false;
          }
          //n-ext:maps-to "../../../../type1-site/type1-site/site-name";
          description
            "type1-sites";
          when " ../type1-site = 'true' ";
        }
        leaf type2-site {
          type boolean;
          description
            "type2-site: True/False";
        }
        leaf-list type2-sites {
          type leafref {
            path "../../../../type2-site/type2-site/site-name";
            require-instance false;
          }
          //n-ext:maps-to "../../../../type2-site/type2-site/site-name";
          description
            "type2-sites";
          when " ../type2-site = 'true' ";
        }
        leaf type3-site {
          type boolean;
          description
            "type3-site: True/False";
        }
        leaf-list type3-sites {
          type leafref {
            path "../../../../type3-site/type3-site/site-name";
            require-instance false;
          }
          //n-ext:maps-to "../../../../type3-site/type3-site/site-name";
          description
            "type3-sites";
          when " ../type3-site = 'true' ";
        }
        leaf type4-site {
          type boolean;
          description
            "type4-site: True/False";
        }
        leaf-list type4-sites {
          type leafref {
            path "../../../../type4-site/type4-site/site-name";
            require-instance false;
          }
          //n-ext:maps-to "../../../../type4-site/type4-site/site-name";
          description
            "type4-sites";
          when " ../type4-site = 'true' ";
        }
      }
    }
    container domain-labels {
      list domain-label {
        key "domain-label-name";
        leaf domain-label-name {
          type string;
          description
            "string";
          mandatory true;
          n-ext:maps-to "/ac:devices/ac:device/wanop-device:label-configuration/domain-label/domain-label-name";
        }
        leaf domain {
          type string;
          description
            "Comma separated domain Eg:<domain or 'domain, ...'>";
          mandatory true;
          n-ext:maps-to "/ac:devices/ac:device/wanop-device:label-configuration/domain-label/domain";
        }
      }
      list update-domain-label {
        n-ext:ignore-for-brownfield;
        key "id";
        leaf id {
          type string;
          description
            "info/description of domain-label or any unique-value as id";
        }
        leaf domain-label-name {
          type leafref {
            path "../../domain-label/domain-label-name";
          }
          description
            "string";
          mandatory true;
          //n-ext:maps-to "/ac:devices/device/wanop-device:label-configuration/domain-label/domain-label-name";
        }
        leaf domain {
          type string;
          description
            "Comma separated domain Eg:<domain or 'domain, ...'>";
          mandatory true;
          //n-ext:maps-to "/ac:devices/device/wanop-device:label-configuration/domain-label/domain";
        }
        leaf operation {
          type operation-def;
          description
            "CREATE
             DELETE
            ";
        }
        leaf type1-site {
          type boolean;
          description
            "type1-site: True/False";
        }
        leaf-list type1-sites {
          type leafref {
            path "../../../../type1-site/type1-site/site-name";
            require-instance false;
          }
          //n-ext:maps-to "../../../../type1-site/type1-site/site-name";
          description
            "type1-sites";
          when " ../type1-site = 'true' ";
        }
        leaf type2-site {
          type boolean;
          description
            "type2-site: True/False";
        }
        leaf-list type2-sites {
          type leafref {
            path "../../../../type2-site/type2-site/site-name";
            require-instance false;
          }
          //n-ext:maps-to "../../../../type2-site/type2-site/site-name";
          description
            "type2-sites";
          when " ../type2-site = 'true' ";
        }
        leaf type3-site {
          type boolean;
          description
            "type3-site: True/False";
        }
        leaf-list type3-sites {
          type leafref {
            path "../../../../type3-site/type3-site/site-name";
            require-instance false;
          }
          //n-ext:maps-to "../../../../type3-site/type3-site/site-name";
          description
            "type3-sites";
          when " ../type3-site = 'true' ";
        }
        leaf type4-site {
          type boolean;
          description
            "type4-site: True/False";
        }
        leaf-list type4-sites {
          type leafref {
            path "../../../../type4-site/type4-site/site-name";
            require-instance false;
          }
          //n-ext:maps-to "../../../../type4-site/type4-site/site-name";
          description
            "type4-sites";
          when " ../type4-site = 'true' ";
        }
      }
    }
    container port-labels {
      list port-label {
        key "port-label-name";
        leaf port-label-name {
          type string;
          description
            "string";
          mandatory true;
          n-ext:maps-to "/ac:devices/ac:device/wanop-device:label-configuration/port-label/port-label-name";
        }
        leaf port {
          type string;
          description
            "Eg:<port numbers> Port numbers separated by ',' or port range separated by '-'";
          mandatory true;
          n-ext:maps-to "/ac:devices/ac:device/wanop-device:label-configuration/port-label/port";
        }
      }
      list update-port-label {
        n-ext:ignore-for-brownfield;
        key "id";
        leaf id {
          type string;
          description
            "info/description of port-label or any unique-value as id";
        }
        leaf port-label-name {
          type leafref {
            path "../../port-label/port-label-name";
          }
          description
            "string";
          mandatory true;
          //n-ext:maps-to "/ac:devices/device/wanop-device:label-configuration/port-label/port-label-name";
        }
        leaf port {
          type string;
          description
            "Eg:<port numbers> Port numbers separated by ',' or port range separated by '-'";
          mandatory true;
        }
        leaf operation {
          type operation-def;
          description
            "CREATE
             DELETE
            ";
        }
        leaf type1-site {
          type boolean;
          description
            "type1-site: True/False";
        }
        leaf-list type1-sites {
          type leafref {
            path "../../../../type1-site/type1-site/site-name";
            require-instance false;
          }
          //n-ext:maps-to "../../../../type1-site/type1-site/site-name";
          description
            "type1-sites";
          when " ../type1-site = 'true' ";
        }
        leaf type2-site {
          type boolean;
          description
            "type2-site: True/False";
        }
        leaf-list type2-sites {
          type leafref {
            path "../../../../type2-site/type2-site/site-name";
            require-instance false;
          }
          //n-ext:maps-to "../../../../type2-site/type2-site/site-name";
          description
            "type2-sites";
          when " ../type2-site = 'true' ";
        }
        leaf type3-site {
          type boolean;
          description
            "type3-site: True/False";
        }
        leaf-list type3-sites {
          type leafref {
            path "../../../../type3-site/type3-site/site-name";
            require-instance false;
          }
          //n-ext:maps-to "../../../../type3-site/type3-site/site-name";
          description
            "type3-sites";
          when " ../type3-site = 'true' ";
        }
        leaf type4-site {
          type boolean;
          description
            "type4-site: True/False";
        }
        leaf-list type4-sites {
          type leafref {
            path "../../../../type4-site/type4-site/site-name";
            require-instance false;
          }
          //n-ext:maps-to "../../../../type4-site/type4-site/site-name";
          description
            "type4-sites";
          when " ../type4-site = 'true' ";
        }
      }
    }
  }

  grouping type2-site-def {
    container cpe-primary {
      uses cpe:cpe-def {
        refine "internal-id" {
          default "cpe-primary";
          config false;
        }
        refine "sequence-number" {
          default "1";
          config false;
        }
        refine "name" {
          default "cpe-primary";
          config false;
        }
      }
      leaf level {
        type uint8;
        description
          "0..255";
        default "2";
        config false;
      }
    }
    container cpe-secondary {
      uses cpe:cpe-def {
        refine "internal-id" {
          default "cpe-secondary";
          config false;
        }
        refine "sequence-number" {
          default "1";
          config false;
        }
        refine "name" {
          default "cpe-secondary";
          config false;
        }
      }
      leaf level {
        type uint8;
        description
          "0..255";
        default "2";
        config false;
      }
    }
    container cpe-primary-cpe-secondary-ic {
      uses ic:interconnect-def {
        refine "name" {
          default "cpe-primary-cpe-secondary-ic";
          config false;
        }
        refine "deploy-on" {
          config false;
        }
        refine "interconnect-name" {
          default "cpe-primary-cpe-secondary-ic";
          config false;
        }
        refine "resource-id" {
          config false;
        }
        refine "sequence-number" {
          default "30";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../cpe-secondary/internal-id";
        }
        description
          "Reference to the endpoint of the interconnect";
        default "cpe-secondary";
        config false;
      }
    }
    container primary-wan {
      uses enf:external-network-def {
        refine "internal-id" {
          default "primary-wan";
          config false;
        }
        refine "sequence-number" {
          default "2";
          config false;
        }
        refine "resource-id" {
          config false;
        }
        refine "deploy-on" {
          config false;
        }
        refine "name" {
          default "primary-wan";
          config false;
        }
      }
      leaf level {
        type uint8;
        description
          "0..255";
        default "1";
        config false;
      }
    }
    container cpe-primary-wan {
      uses ic:interconnect-def {
        refine "name" {
          default "cpe-primary-wan";
          config false;
        }
        refine "deploy-on" {
          config false;
        }
        refine "interconnect-name" {
          default "cpe-primary-wan";
          config false;
        }
        refine "resource-id" {
          config false;
        }
        refine "sequence-number" {
          default "34";
          config false;
        }
        refine "internal-id" {
          config false;
        }
        refine "type" {
          config false;
        }
      }
      leaf endpoint1 {
        n-ext:end-point;
        type leafref {
          path "../../primary-wan/internal-id";
        }
        description
          "Reference to the endpoint of the interconnect";
        default "primary-wan";
        config false;
      }
      leaf endpoint2 {
        n-ext:end-point;
        type leafref {
          path "../../cpe-primary/internal-id";
        }
        description
          "Reference to the endpoint of the interconnect";
        default "cpe-primary";
        config false;
      }
    }
    container secondary-wan {
      uses enf:external-network-def {
        refine "internal-id" {
          default "secondary-wan";
          config false;
        }
        refine "sequence-number" {
          default "37";
          config false;
        }
        refine "resource-id" {
          config false;
        }
        refine "deploy-on" {
          config false;
        }
        refine "name" {
          default "secondary-wan";
          config false;
        }
      }
      leaf level {
        type uint8;
        description
          "0..255";
        default "1";
        config false;
      }
    }
    container cpe-secondary-wan {
      uses ic:interconnect-def {
        refine "name" {
          default "cpe-secondary-wan";
          config false;
        }
        refine "deploy-on" {
          config false;
        }
        refine "interconnect-name" {
          default "cpe-secondary-wan";
          config false;
        }
        refine "resource-id" {
          config false;
        }
        refine "sequence-number" {
          default "38";
          config false;
        }
        refine "internal-id" {
          config false;
        }
        refine "type" {
          config false;
        }
      }
      leaf endpoint1 {
        n-ext:end-point;
        type leafref {
          path "../../secondary-wan/internal-id";
        }
        description
          "Reference to the endpoint of the interconnect";
        default "secondary-wan";
        config false;
      }
      leaf endpoint2 {
        n-ext:end-point;
        type leafref {
          path "../../cpe-secondary/internal-id";
        }
        description
          "Reference to the endpoint of the interconnect";
        default "cpe-secondary";
        config false;
      }
    }
    container wanop-primary {
      uses wanop:wanoptimizer-def {
        refine "internal-id" {
          default "wanop-primary";
          config false;
        }
        refine "sequence-number" {
          default "3";
          config false;
        }
      }
      leaf level {
        type uint8;
        description
          "0..255";
        default "3";
        config false;
      }
      leaf device-ip {
        type leafref {
          path "/rp:resource-pools/rp:resource-pool[rp:name=current()/../../resource-pool]/rp:device/rp:id";
        }
        description
          "device-ip";
        n-ext-ui:ncx-ext-allowed-vals "/ac:devices/ac:device[ac:device-type='Steelhead WAN Optimizer']/ac:id";
      }
      uses wanop-associated-services;
      container wanop-endpoints {
        uses wanop-ic-local-props-type2;
      }
      container routes {
        uses routes;
      }
    }
    container wanop-secondary {
      uses wanop:wanoptimizer-def {
        refine "internal-id" {
          default "wanop-secondary";
          config false;
        }
        refine "sequence-number" {
          default "4";
          config false;
        }
      }
      leaf level {
        type uint8;
        description
          "0..255";
        default "4";
        config false;
      }
      leaf device-ip {
        type leafref {
          path "/rp:resource-pools/rp:resource-pool[rp:name=current()/../../resource-pool]/rp:device/rp:id";
        }
        description
          "device-ip";
        n-ext-ui:ncx-ext-allowed-vals "/ac:devices/ac:device[ac:device-type='Steelhead WAN Optimizer']/ac:id";
      }
      uses wanop-associated-services;
      container wanop-endpoints {
        uses wanop-ic-local-props-type2;
      }
      container routes {
        uses routes;
      }
    }
    container cpe-wanop {
      uses ic:interconnect-def {
        refine "name" {
          default "cpe-wanop";
          config false;
        }
        refine "deploy-on" {
          config false;
        }
        refine "resource-id" {
          config false;
        }
        refine "interconnect-name" {
          default "cpe-wanop";
          config false;
        }
        refine "sequence-number" {
          default "7";
          config false;
        }
        refine "internal-id" {
          config false;
        }
        refine "type" {
          config false;
        }
      }
      leaf endpoint1 {
        n-ext:end-point;
        type leafref {
          path "../../cpe-primary/internal-id";
        }
        description
          "Reference to the endpoint of the interconnect";
        default "cpe-primary";
        config false;
      }
      leaf endpoint2 {
        n-ext:end-point;
        type leafref {
          path "../../wanop-primary/internal-id";
        }
        description
          "Reference to the endpoint of the interconnect";
        default "wanop-primary";
        config false;
      }
      leaf endpoint3 {
        n-ext:end-point;
        type leafref {
          path "../../cpe-secondary/internal-id";
        }
        description
          "Reference to the endpoint of the interconnect";
        default "cpe-secondary";
        config false;
      }
    }
    container wanop-wanop {
      uses ic:interconnect-def {
        refine "name" {
          default "wanop-wanop";
          config false;
        }
        refine "deploy-on" {
          config false;
        }
        refine "resource-id" {
          config false;
        }
        refine "interconnect-name" {
          default "wanop-wanop";
          config false;
        }
        refine "sequence-number" {
          default "7";
          config false;
        }
        refine "internal-id" {
          config false;
        }
        refine "type" {
          config false;
        }
      }
      leaf endpoint1 {
        n-ext:end-point;
        type leafref {
          path "../../wanop-primary/internal-id";
        }
        description
          "Reference to the endpoint of the interconnect";
        default "wanop-primary";
        config false;
      }
      leaf endpoint2 {
        n-ext:end-point;
        type leafref {
          path "../../wanop-secondary/internal-id";
        }
        description
          "Reference to the endpoint of the interconnect";
        default "wanop-secondary";
        config false;
      }
    }
    container lan {
      uses vnf:virtual-network-def {
        refine "internal-id" {
          default "lan";
          config false;
        }
        refine "sequence-number" {
          default "41";
          config false;
        }
        refine "resource-id" {
          config false;
        }
        refine "deploy-on" {
          config false;
        }
        refine "name" {
          default "lan";
          config false;
        }
      }
      leaf level {
        type uint8;
        description
          "0..255";
        default "5";
        config false;
      }
    }
    container wanop-lan {
      uses ic:interconnect-def {
        refine "name" {
          default "wanop-lan";
          config false;
        }
        refine "deploy-on" {
          config false;
        }
        refine "resource-id" {
          config false;
        }
        refine "interconnect-name" {
          default "wanop-lan";
          config false;
        }
        refine "sequence-number" {
          default "6";
          config false;
        }
        refine "internal-id" {
          config false;
        }
        refine "type" {
          config false;
        }
      }
      leaf endpoint1 {
        n-ext:end-point;
        type leafref {
          path "../../wanop-secondary/internal-id";
        }
        description
          "Reference to the endpoint of the interconnect";
        default "wanop-secondary";
        config false;
      }
      leaf endpoint2 {
        n-ext:end-point;
        type leafref {
          path "../../lan/internal-id";
        }
        description
          "Reference to the endpoint of the interconnect";
        default "lan";
        config false;
      }
    }
  }

  grouping type1-site-def {
    container cpe {
      uses cpe:cpe-def {
        refine "internal-id" {
          default "cpe";
          config false;
        }
        refine "sequence-number" {
          default "2";
          config false;
        }
        refine "name" {
          default "cpe";
          config false;
        }
      }
      leaf level {
        type uint8;
        description
          "0..255";
        default "2";
        config false;
      }
    }
    container wanop {
      uses wanop:wanoptimizer-def {
        refine "internal-id" {
          default "wanop";
          config false;
        }
        refine "sequence-number" {
          default "3";
          config false;
        }
      }
      leaf level {
        type uint8;
        description
          "0..255";
        default "3";
        config false;
      }
      leaf device-ip {
        type leafref {
          path "/rp:resource-pools/rp:resource-pool[rp:name=current()/../../resource-pool]/rp:device/rp:id";
        }
        description
          "device-ip";
        n-ext-ui:ncx-ext-allowed-vals "/ac:devices/ac:device[ac:device-type='Steelhead WAN Optimizer']/ac:id";
      }
      uses wanop-associated-services;
      container wanop-endpoints {
        uses wanop-ic-local-props-type1;
      }
      container routes {
        uses routes;
      }
    }
    container wan {
      uses enf:external-network-def {
        refine "internal-id" {
          default "wan";
          config false;
        }
        refine "sequence-number" {
          default "1";
          config false;
        }
        refine "resource-id" {
          config false;
        }
        refine "deploy-on" {
          config false;
        }
        refine "name" {
          default "wan";
          config false;
        }
      }
      leaf level {
        type uint8;
        description
          "0..255";
        default "1";
        config false;
      }
    }
    container wan-cpe {
      uses ic:interconnect-def {
        refine "name" {
          default "wan-cpe";
          config false;
        }
        refine "deploy-on" {
          config false;
        }
        refine "resource-id" {
          config false;
        }
        refine "interconnect-name" {
          default "wan-cpe";
          config false;
        }
        refine "sequence-number" {
          default "4";
          config false;
        }
        refine "internal-id" {
          config false;
        }
        refine "type" {
          config false;
        }
      }
      leaf endpoint1 {
        n-ext:end-point;
        type leafref {
          path "../../wan/internal-id";
        }
        description
          "Reference to the endpoint of the interconnect";
        default "wan";
        config false;
      }
      leaf endpoint2 {
        n-ext:end-point;
        type leafref {
          path "../../cpe/internal-id";
        }
        description
          "Reference to the endpoint of the interconnect";
        default "cpe";
        config false;
      }
    }
    container lan {
      uses vnf:virtual-network-def {
        refine "internal-id" {
          default "lan";
          config false;
        }
        refine "sequence-number" {
          default "5";
          config false;
        }
        refine "resource-id" {
          config false;
        }
        refine "deploy-on" {
          config false;
        }
        refine "name" {
          default "lan";
          config false;
        }
      }
      leaf level {
        type uint8;
        description
          "0..255";
        default "4";
        config false;
      }
    }
    container wanop-lan {
      uses ic:interconnect-def {
        refine "name" {
          default "wanop-lan";
          config false;
        }
        refine "deploy-on" {
          config false;
        }
        refine "resource-id" {
          config false;
        }
        refine "interconnect-name" {
          default "wanop-lan";
          config false;
        }
        refine "sequence-number" {
          default "6";
          config false;
        }
        refine "internal-id" {
          config false;
        }
        refine "type" {
          config false;
        }
      }
      leaf endpoint1 {
        n-ext:end-point;
        type leafref {
          path "../../wanop/internal-id";
        }
        description
          "Reference to the endpoint of the interconnect";
        default "wanop";
        config false;
      }
      leaf endpoint2 {
        n-ext:end-point;
        type leafref {
          path "../../lan/internal-id";
        }
        description
          "Reference to the endpoint of the interconnect";
        default "lan";
        config false;
      }
    }
    container cpe-wanop {
      uses ic:interconnect-def {
        refine "name" {
          default "cpe-wanop";
          config false;
        }
        refine "deploy-on" {
          config false;
        }
        refine "resource-id" {
          config false;
        }
        refine "interconnect-name" {
          default "cpe-wanop";
          config false;
        }
        refine "sequence-number" {
          default "7";
          config false;
        }
        refine "internal-id" {
          config false;
        }
        refine "type" {
          config false;
        }
      }
      leaf endpoint1 {
        n-ext:end-point;
        type leafref {
          path "../../cpe/internal-id";
        }
        description
          "Reference to the endpoint of the interconnect";
        default "cpe";
        config false;
      }
      leaf endpoint2 {
        n-ext:end-point;
        type leafref {
          path "../../wanop/internal-id";
        }
        description
          "Reference to the endpoint of the interconnect";
        default "wanop";
        config false;
      }
    }
  }

  grouping wanop-associated-services {
    container applications {
      list applications {
        key "name";
        leaf name {
          type leafref {
            path "/ac:services/managed-cpe-services/customer/wanop-services/applications/application/application-name";
          }
          description
            "name";
        }
      }
    }
    container inpath-rules {
      uses inpath-rules-def;
    }
  }

  grouping wanop-ic-local-props-type1 {
    list wanop-endpoint {
      key "interface-name";
      leaf interface-name {
        type leafref {
          path "/ac:devices/ac:device[ac:id=current()/../../../device-ip]/if:interfaces/if:interface/if:long-name";
        }
        description
          "interface-name";
        n-ext:maps-to "/ac:devices/device/if:interfaces/interface/name";
        n-ext:maps-to "/ac:devices/device/if:interfaces/interface/long-name";
        n-ext:ncx-add-reference-false;
        //mandatory true;
      }
      leaf profile-name {
        type leafref {
          path "/ac:services/cpedeployment:managed-cpe-services/customer[name=current()/../../../../../../../name]/single-cpe-site/single-cpe-site-services[site-name=current()/../../../../single-cpe-sites]/cpe-lan/lan-profile/profile-name";
        }
        description
          "profile-name";
        when "../interface-name != 'aux'";
        //n-ext:maps-to "/ac:services/cpedeployment:managed-cpe-services/customer[name=current()/../../../../../../../name]/single-cpe-site/single-cpe-site-services/cpe-lan/lan-profile/profile-name";
      }
      leaf enable-optimization {
        type enumeration {
          enum "enable";
        }
        default "enable";
        when "../interface-name != 'aux'";
        description
          "enable-optimization only for inpath-interfaces";
      }
      uses wanop-end-point-props;
    }
  }

  grouping wanop-ic-local-props-type2 {
    list wanop-endpoint {
      key "interface-name";
      leaf interface-name {
        type leafref {
          path "/ac:devices/ac:device[ac:id=current()/../../../device-ip]/if:interfaces/if:interface/if:long-name";
        }
        description
          "interface-name";
        n-ext:maps-to "/ac:devices/device/if:interfaces/interface/name";
        n-ext:maps-to "/ac:devices/device/if:interfaces/interface/long-name";
        //mandatory true;
      }
      leaf profile-name {
        type leafref {
          path "/ac:services/cpedeployment:managed-cpe-services/customer[name=current()/../../../../../../../name]/dual-cpe-site/dual-cpe-site-services[site-name=current()/../../../../dual-cpe-sites]/cpe-lan/lan-profile/profile-name";
        }
        description
          "profile-name";
        when "../interface-name != 'aux'";
        //n-ext:maps-to "/ac:services/cpedeployment:managed-cpe-services/customer[name=current()/../../../../../../../name]/dual-cpe-site/dual-cpe-site-services/cpe-lan/lan-profile/profile-name";
        mandatory true;
      }
      leaf enable-optimization {
        type enumeration {
          enum "enable";
        }
        default "enable";
        when "../interface-name != 'aux'";
        description
          "enable-optimization only for inpath-interfaces";
      }
      uses wanop-end-point-props;
    }
  }

  grouping wanop-end-point-props {
    leaf cidr {
      type inet:ipv4-prefix;
      description
        "valid cidr";
      when "../interface-name = 'aux'";
      mandatory true;
    }
    leaf interface-ip {
      type inet:ipv4-address;
      description
        "Valid IPv4 Address (A.B.C.D for e.x: 172.16.1.1)";
      n-ext:maps-to "/ac:devices/ac:device/if:interfaces/interface/ip-address";
    }
    leaf interface-description {
      type string-no-lead-trail-space;
      description
        "string";
      n-ext:maps-to "/ac:devices/ac:device/if:interfaces/interface/description";
    }
    leaf gateway-ip {
      type inet:ipv4-address;
      description
        "cpe ip";
      when "../interface-name != 'aux'";
      n-ext:maps-to "/ac:devices/ac:device/if:interfaces/interface/inpath-gateway";
    }
    leaf speed {
      type enumeration {
        enum "10";
        enum "100";
        enum "1000";
        enum "10000";
        enum "auto";
      }
      description
        "Speed in Mbps, Example: 10, 100, 1000, auto";
      n-ext:maps-to "/ac:devices/ac:device/if:interfaces/interface/link-speed";
    }
    leaf duplex {
      type enumeration {
        enum "half";
        enum "full";
        enum "auto";
      }
      description
        "Duplex options, 'auto' or 'full' or 'half' ";
      n-ext:maps-to "/ac:devices/ac:device/if:interfaces/interface/duplex";
    }
    leaf mtu {
      type string;
      description
        "string";
      n-ext:maps-to "/ac:devices/ac:device/if:interfaces/interface/mtu";
    }
    leaf vlan-id {
      type uint32 {
        range "1..4096";
      }
      description
        "1..4096";
      when "../interface-name != 'aux'";
      n-ext:maps-to "/ac:devices/ac:device/if:interfaces/interface/port-number-vlan";
    }
  }

  grouping key-chain-def {
    container key-chain {
      list router-key-chain {
        key "key-chain-name";
        leaf key-chain-name {
          type string;
          description
            "string";
          n-ext:maps-to "/ac:devices/ac:device/l3features:key-chain/router-key-chain/key-chain-name";
        }
        list keys {
          key "key-identifier";
          leaf key-identifier {
            type uint64;
            description
              "0..18446744073709551615";
            n-ext:maps-to "/ac:devices/ac:device/l3features:key-chain/router-key-chain[key-chain-name=current()/../../key-chain-name]/keys/key-identifier";
          }
          leaf key-string-password {
            type string;
            description
              "string";
            n-ext:maps-to "/ac:devices/ac:device/l3features:key-chain/router-key-chain[key-chain-name=current()/../../key-chain-name]/keys/key-string-password";
          }
        }
      }
    }
  }

  grouping analytics-def {
    leaf update-supported-from-introducing-green-brown-fields {
      type boolean;
      description
        "update-supported-from-introducing-green-brown-fields: True/False";
    }
    leaf last-7-days {
      type string;
      description
        "string";
      config false;
    }
    leaf last-7-days-green {
      type string;
      description
        "string";
      config false;
    }
    leaf last-7-days-brown {
      type string;
      description
        "string";
      config false;
    }
    leaf last-15-days {
      type string;
      description
        "string";
      config false;
    }
    leaf last-15-days-green {
      type string;
      description
        "string";
      config false;
    }
    leaf last-15-days-brown {
      type string;
      description
        "string";
      config false;
    }
    leaf last-30-days {
      type string;
      description
        "string";
      config false;
    }
    leaf last-30-days-green {
      type string;
      description
        "string";
      config false;
    }
    leaf last-30-days-brown {
      type string;
      description
        "string";
      config false;
    }
  }

  augment "/ac:services" {
    container managed-cpe-services {
      list customer {
        key "name";
        uses dmvpn-tunnel-profile-def;
        uses domain-def;
        uses ipsec-def;
        uses qos-def;
        uses route-maps-def;
        uses prefix-lists-def;
        uses community-lists-def;
        //uses extcommunity-lists-def;
        uses dc-def;
        uses cpe-deployment-def;
        uses cpe-deployment-def-dual;
        uses dc-def-dual;
        uses vrf-def;
        uses wanop-def;
        uses cpe-tertiary-def;
        uses key-chain-def;
        container access-lists {
          //n-ext:ignore-for-brownfield;
          list access-list {
            key "name";
            uses acl-def;
          }
          list update-access-list {
            n-ext:ignore-for-brownfield;
            key "id";
            uses update-acl-def;
          }
          list delete-access-list {
            n-ext:ignore-for-brownfield;
            key "id";
            uses delete-acl-def;
          }
        }
        uses dps-def;
        container object-groups {
          //n-ext:ignore-for-brownfield;
          list object-group {
            key "name";
            uses object-group-def;
          }
          list delete-object-group {
            n-ext:ignore-for-brownfield;
            key "id";
            uses delete-object-group-def;
          }
        }
        container as-path-acls {
          //n-ext:ignore-for-brownfield;
          list as-path-acl {
            key "number condition expression";
            uses as-path-acl;
          }
        }
        container bgp-peer-groups {
          //n-ext:ignore-for-brownfield;
          list bgp-peer-group {
            key "peer-group";
            uses bgp-peer-props1;
          }
        }
        container adaptive-dps-eem-applet {
          uses adaptive-dps;
        }
        container analytics {
          uses analytics-def;
        }
      }
    }
  }
  rpc cpedeployment-ipsla-threshold-violation-event-handler {
    description
      "ipsla threshold violation event handler";
    input {
      anyxml payload;
    }
    output {
      anyxml payload;
    }
  }
}
