module wanoptimizer-feature {
  yang-version 1;
  namespace "http://anutanetworks.com/wanoptimizer-feature";
  prefix wanop;

  import controller {
    prefix ac;
  }
  import interface {
    prefix if;
  }
  import ietf-inet-types {
    prefix inet;
  }
  import service-manager {
    prefix sm;
  }
  import ncx-extensions {
    prefix n-ext;
  }
  import resourcepool {
    prefix rp;
  }

  organization "Anuta Networks";

  revision 2016-09-29 {
    description
      "Updated for NCX 5.5";
  }


  grouping wanoptimizer-def {
    n-ext:ncx-feature "wanoptimizer";
    leaf name {
      type string;
      mandatory true;
    }
    leaf internal-id {
      type string;
      description
        "Internal Id to identify the Resource";
    }
    leaf sequence-number {
      type uint16;
      description
        "User-specified sequence number to specify the order in which feature would be executed";
      default "1";
    }
  }

}
