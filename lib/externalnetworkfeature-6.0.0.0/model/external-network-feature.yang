module external-network-feature {
  yang-version 1;
  namespace "http://anutanetworks.com/externalnetworkfeature";
  prefix enf;

  import service-manager {
    prefix sm;
  }
  import ncx-extensions {
    prefix n-ext;
  }

  organization "Anuta Networks";
  description
    "This module contains a collection of YANG definitions for
         external network and its associated features";

  revision 2016-09-29 {
    description
      "Updated for NCX 5.5";
  }

  grouping external-network-def {
    n-ext:ncx-feature "externalnetwork";
    description
      "external network resource parameters.";
    uses sm:resource-def;
  }
}
