module vrouter-feature {
  yang-version 1;
  namespace "http://anutanetworks.com/vrouter-feature";
  prefix vrf;

  import controller {
    prefix ac;
  }
  import interface {
    prefix if;
  }
  import ietf-inet-types {
    prefix inet;
  }
  import service-manager {
    prefix sm;
  }
  import ncx-extensions {
    prefix n-ext;
  }

  organization "Anuta Networks";

  revision 2016-09-29 {
    description
      "Updated for NCX 5.5";
  }

  grouping static-route {
    leaf dest-ip-address {
      type inet:ipv4-address;
      description
        "Accepts CIDR(e.g. 172.16.1.0/8)";
      mandatory true;
    }
    leaf dest-mask {
      type inet:ipv4-address;
      mandatory true;
    }
    leaf next-hop-ip {
      type inet:ipv4-address;
      config false;
    }
    leaf description {
      type string;
      config false;
    }
    leaf metric {
      type uint32;
      config false;
    }
    leaf interface-name {
      type string;
      description
        "interface-name";
      config false;
    }
    leaf seq-num {
      type uint32;
      config false;
    }
    leaf name {
      type string;
      config false;
    }
    leaf vrf {
      type string;
      config false;
    }
    leaf tag {
      type uint32;
      config false;
    }
    list options {
      key "id";
      leaf sequence-number {
        type uint8;
        default "100";
        config false;
      }
      leaf id {
	type string;
      }
      leaf next-hop-ip {
        type inet:ipv4-address;        
      }
      leaf global-address {
        type boolean;
      }
      leaf metric {
        type uint32;              
      }
      leaf interface-name {
        type string;                
      }      
      leaf name {
        type string;         
      }
      leaf vrf {
        type string;  
      }
      leaf tag {
        type uint32;             
      }
      leaf permanent {
        type boolean;             
      }
      leaf track {
        type uint16;
      }
      leaf description {
        type string;
      }
      leaf seq-num {
        type uint32;
      }
    }
  }

  grouping vrouter-def {
    n-ext:ncx-feature "vrouter";
    leaf vrf-name {
      type string;
      //mandatory true;
    }
    container static-routes {
      list static-route {
        key "dest-ip-address dest-mask";
        uses static-route;
        leaf sequence-number {
          type uint8;
          default "99";
          config false;
        }
      }
    }
    uses sm:resource-def;
  }
}
