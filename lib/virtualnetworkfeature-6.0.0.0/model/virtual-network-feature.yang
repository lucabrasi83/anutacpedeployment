module virtual-network-feature {
  yang-version 1;
  namespace "http://anutanetworks.com/virtualnetworkfeature";
  prefix vnf;

  import service-manager {
    prefix sm;
  }
  import ncx-extensions {
    prefix n-ext;
  }

  organization
    "Anuta Networks";
  description
    "This module contains a collection of YANG definitions for
         virtual network and its associated features";

  revision 2016-09-29 {
    description
      "Updated for NCX 5.5";
  }
  revision 2016-05-12 {
    description
      "Initial revision";
  }

  grouping virtual-network-def {
    n-ext:ncx-feature "virtualnetwork";
    description
      "virtual network resource parameters.";
    uses sm:resource-def;
  }
}
